TCAP-Definitions-Para DEFINITIONS  ::=

BEGIN

IMPORTS
  LocationNotificationArg,
  LCS-MOLRArg,
  LocationNotificationRes,
  LCS-MOLRRes,
  SystemFailureParam,
  UnexpectedDataParam,
  DataMissingParam,
  FacilityNotSupParam,
  SS-SubscriptionViolationParam,
  PositionMethodFailure-Param

FROM LCS-Definitions-Arguments

RegisterSS-Arg,
InterrogateSS-Res,
NotifySS-Arg,
SS-Info,
SS-ForBS-Code,
CallBarredParam,
BearerServNotProvParam,
TeleservNotProvParam,
IllegalSS-OperationParam,
IllegalSubscriberParam,
IllegalEquipmentParam,
SS-IncompatibilityCause,
SS-ErrorStatus,
SS-NotAvailable,
SS-Code,
GuidanceInfo,
SS-UserData,
USSD-Arg,
USSD-Res,
Password,
PW-RegistrationFailureCause,
AbsentSubscriberParam
FROM SS-Definitions-Arguments;

--*****************************************************
--Derived from SS-DataTypes in 3GPP TS 24.080
--*****************************************************



InvokeArgument  ::= CHOICE {
                            registerSS      [0] EXPLICIT RegisterSS-Arg,  
                            eraseSS         [1] EXPLICIT SS-ForBS-Code,
                            activateSS      [2] EXPLICIT SS-ForBS-Code,
                            deactivateSS    [3] EXPLICIT SS-ForBS-Code,
                            interrogateSS   [4] EXPLICIT SS-ForBS-Code,  
                            registerPassword [5] EXPLICIT SS-Code,
                            getPassword     [6] EXPLICIT GuidanceInfo,
                            processUnstructuredSS-Data [7] EXPLICIT SS-UserData,
                            processUnstructuredSS-Request [8] EXPLICIT USSD-Arg,
                            unstructuredSS-Request [9] EXPLICIT USSD-Arg,
                            unstructuredSS-Notify [10] EXPLICIT USSD-Arg,
                            notifySS        [11] EXPLICIT NotifySS-Arg,
                            buildMPTY       [12] EXPLICIT NULL, -- EXPLICIT,
                            holdMPTY        [13] EXPLICIT NULL, -- EXPLICIT,
                            retrieveMPTY    [14] EXPLICIT NULL, -- EXPLICIT,
                            splitMPTY       [15] EXPLICIT NULL, -- EXPLICIT,
                            explicitCT      [16] EXPLICIT NULL, -- EXPLICIT,
                            lcsNotification	[17] EXPLICIT LocationNotificationArg,
							lcs-MOLR		[18] EXPLICIT LCS-MOLRArg
							}


ReturnRes		::= CHOICE {
                            registerSSRes   [0] EXPLICIT SS-Info,  
                            eraseSS         [1] EXPLICIT SS-Info,
                            activateSS      [2] EXPLICIT SS-Info,
                            deactivateSS    [3] EXPLICIT SS-Info,
                            interrogateSSRes    [4] EXPLICIT InterrogateSS-Res, 
                            registerPassword [5] EXPLICIT Password,
                            getPassword     [6] EXPLICIT Password,
                            processUnstructuredSS-Data [7] EXPLICIT SS-UserData,
                            processUnstructuredSS-Request [8] EXPLICIT USSD-Res,
                            unstructuredSS-Request [9] EXPLICIT USSD-Res,
                            unstructuredSS-Notify [10] EXPLICIT NULL, -- EXPLICIT,
                            notifySS        [11] EXPLICIT NULL, -- EXPLICIT,
                            buildMPTY       [12] EXPLICIT NULL, -- EXPLICIT,
                            holdMPTY        [13] EXPLICIT NULL, -- EXPLICIT,
                            retrieveMPTY    [14] EXPLICIT NULL, -- EXPLICIT,
                            splitMPTY       [15] EXPLICIT NULL, -- EXPLICIT,
                            explicitCT      [16] EXPLICIT NULL, -- EXPLICIT,
							lcsNotifficationRes	[17] EXPLICIT LocationNotificationRes,
							lcsMOLRRes			[18] EXPLICIT LCS-MOLRRes
							}


ReturnErrPara	::= CHOICE {
                            registerSSRes       [0] EXPLICIT RegisterSSErrPara, 
                            eraseSS         [1] EXPLICIT EraseSSErrPara,
                            activateSS      [2] EXPLICIT ActivateSSErrPara,
                            deactivateSS    [3] EXPLICIT ActivateSSErrPara,
                            interrogateSSRes    [4] EXPLICIT InterrogateSSErrPara, 
                            registerPassword [5] EXPLICIT RegisterPasswordErrPara,
                            getPassword     [6] EXPLICIT NULL,
                            processUnstructuredSS-Data [7] EXPLICIT DataErrPara,
                            processUnstructuredSS-Request [8] EXPLICIT ProcessUSSReqErrPara,
                            unstructuredSS-Request [9] EXPLICIT USSDErrPara,
                            unstructuredSS-Notify [10] EXPLICIT USSDErrPara,
                            notifySS        [11] EXPLICIT NULL,
                            buildMPTY       [12] EXPLICIT BuildMPTYErrPara,
                            holdMPTY        [13] EXPLICIT MPTYErrPara,
                            retrieveMPTY    [14] EXPLICIT MPTYErrPara,
                            splitMPTY       [15] EXPLICIT MPTYErrPara,
                            explicitCT      [16] EXPLICIT ExplicitCTErrPara,
							lcsNotifficationErrPara	[17] EXPLICIT	DataErrPara,
							lcs-MOLR-ResErrPara		[18] EXPLICIT	Lcs-MOLR-ErrPara
							}

DataErrPara    ::= CHOICE {
	systemFailure		[0] EXPLICIT 	SystemFailureParam,
	unexpectedDataValue [1] EXPLICIT	UnexpectedDataParam
	}

Lcs-MOLR-ErrPara ::= CHOICE {
	systemFailure				[0] EXPLICIT	SystemFailureParam,
	unexpectedDataValue 		[1] EXPLICIT	UnexpectedDataParam,
	dataMissing					[2] EXPLICIT	DataMissingParam,
	facilityNotSupported 		[3] EXPLICIT	FacilityNotSupParam,
	ss-SubscriptionViolation 	[4] EXPLICIT	SS-SubscriptionViolationParam,
	positionMethodFailure		[5] EXPLICIT	PositionMethodFailure-Param,
	... 
	}

RegisterSSErrPara ::= CHOICE {
	systemFailure				[0] EXPLICIT	SystemFailureParam,
	unexpectedDataValue 		[1] EXPLICIT	UnexpectedDataParam,
	dataMissing					[2] EXPLICIT	DataMissingParam,
	bearerServiceNotProvisioned [3] EXPLICIT	BearerServNotProvParam,
	teleServiceNotProvisioned   [4] EXPLICIT	TeleservNotProvParam,
	callBarred          		[5] EXPLICIT	CallBarredParam,
	illegalSSOperation     		[6] EXPLICIT	IllegalSS-OperationParam,
	ss-ErrorStatus       		[7] EXPLICIT	SS-ErrorStatus,
	ss-Incompatibility     		[8] EXPLICIT	SS-IncompatibilityCause,
	... 
}

EraseSSErrPara ::= CHOICE {
	systemFailure				[0] EXPLICIT	SystemFailureParam,
	dataMissing					[1] EXPLICIT	DataMissingParam,
	unexpectedDataValue 		[2] EXPLICIT	UnexpectedDataParam,
	bearerServiceNotProvisioned [3] EXPLICIT	BearerServNotProvParam,
	teleServiceNotProvisioned   [4] EXPLICIT	TeleservNotProvParam,
	callBarred          		[5] EXPLICIT	CallBarredParam,
	illegalSSOperation     		[6] EXPLICIT	IllegalSS-OperationParam,
	ss-ErrorStatus       		[7] EXPLICIT	SS-ErrorStatus,
	... 
}

InterrogateSSErrPara ::= CHOICE {
	systemFailure				[0] EXPLICIT	SystemFailureParam,
	unexpectedDataValue 		[1] EXPLICIT	UnexpectedDataParam,
	dataMissing					[2] EXPLICIT	DataMissingParam,
	bearerServiceNotProvisioned [3] EXPLICIT	BearerServNotProvParam,
	teleServiceNotProvisioned   [4] EXPLICIT	TeleservNotProvParam,
	callBarred          		[5] EXPLICIT	CallBarredParam,
	illegalSSOperation     		[6] EXPLICIT	IllegalSS-OperationParam,
	ss-NotAvailable       		[7] EXPLICIT	SS-NotAvailable,
	... 
}

ActivateSSErrPara ::= CHOICE {
	systemFailure				[0] EXPLICIT	SystemFailureParam,
	dataMissing					[1] EXPLICIT	DataMissingParam,
	unexpectedDataValue 		[2] EXPLICIT	UnexpectedDataParam,
	bearerServiceNotProvisioned [3] EXPLICIT	BearerServNotProvParam,
	teleServiceNotProvisioned   [4] EXPLICIT	TeleservNotProvParam,
	callBarred          		[5] EXPLICIT	CallBarredParam,
	illegalSSOperation     		[6] EXPLICIT	IllegalSS-OperationParam,
	ss-ErrorStatus       		[7] EXPLICIT	SS-ErrorStatus,
	ss-SubscriptionViolation 	[8] EXPLICIT	SS-SubscriptionViolationParam,
    negativePW-Check            [9] EXPLICIT NULL, -- EXPLICIT,
    numberOfPW-AttemptsViolation [10] EXPLICIT NULL, -- EXPLICIT,
	... 
}

RegisterPasswordErrPara ::= CHOICE {
	systemFailure				[0] EXPLICIT	SystemFailureParam,
	dataMissing					[1] EXPLICIT	DataMissingParam,
	unexpectedDataValue 		[2] EXPLICIT	UnexpectedDataParam,
	callBarred          		[3] EXPLICIT	CallBarredParam,
	ss-SubscriptionViolation 	[4] EXPLICIT	SS-SubscriptionViolationParam,
    pw-RegistrationFailure      [5] EXPLICIT PW-RegistrationFailureCause,
    negativePW-Check            [6] EXPLICIT NULL, -- EXPLICIT,
    numberOfPW-AttemptsViolation [7] EXPLICIT NULL, -- EXPLICIT,
	... 
}

ProcessUSSReqErrPara ::= CHOICE {
	systemFailure				[0] EXPLICIT	SystemFailureParam,
	dataMissing					[1] EXPLICIT	DataMissingParam,
	unexpectedDataValue 		[2] EXPLICIT	UnexpectedDataParam,
    unknownAlphabet             [3] EXPLICIT NULL, -- EXPLICIT,
	callBarred          		[4] EXPLICIT	CallBarredParam,
	... 
}

USSDErrPara ::= CHOICE {
	systemFailure				[0] EXPLICIT	SystemFailureParam,
	dataMissing					[2] EXPLICIT	DataMissingParam,
	unexpectedDataValue 		[1] EXPLICIT	UnexpectedDataParam,
    absentSubscriber            [3] EXPLICIT    AbsentSubscriberParam,
    illegalSubscriber           [4] EXPLICIT    IllegalSubscriberParam,
    illegalEquipment            [5] EXPLICIT    IllegalEquipmentParam,
    unknownAlphabet             [6] EXPLICIT NULL, -- EXPLICIT,
    ussd-Busy                   [7] EXPLICIT NULL, -- EXPLICIT,
	... 
}

BuildMPTYErrPara ::= CHOICE {
	illegalSSOperation     		[0] EXPLICIT	IllegalSS-OperationParam,
	ss-ErrorStatus       		[1] EXPLICIT	SS-ErrorStatus,
	ss-NotAvailable       		[2] EXPLICIT	SS-NotAvailable,
	ss-Incompatibility     		[3] EXPLICIT	SS-IncompatibilityCause,
	systemFailure				[4] EXPLICIT	SystemFailureParam,
    resourcesNotAvailable       [5] NULL, -- EXPLICIT,
	maxNumberOfMPTY-ParticipantsExceeded [6] EXPLICIT	NULL, -- EXPLICIT,
	... 
}

MPTYErrPara ::= CHOICE {
	illegalSSOperation     		[0] EXPLICIT	IllegalSS-OperationParam,
	ss-ErrorStatus       		[1] EXPLICIT	SS-ErrorStatus,
	ss-Incompatibility     		[2] EXPLICIT	SS-IncompatibilityCause,
	facilityNotSupported 		[3] EXPLICIT	FacilityNotSupParam,
	systemFailure				[4] EXPLICIT	SystemFailureParam,
	... 
}

ExplicitCTErrPara ::= CHOICE {
	illegalSSOperation     		[0] EXPLICIT	IllegalSS-OperationParam,
	ss-ErrorStatus       		[1] EXPLICIT	SS-ErrorStatus,
	ss-NotAvailable       		[2] EXPLICIT	SS-NotAvailable,
	ss-Incompatibility     		[3] EXPLICIT	SS-IncompatibilityCause,
	facilityNotSupported 		[4] EXPLICIT	FacilityNotSupParam,
	systemFailure				[5] EXPLICIT	SystemFailureParam,
    resourcesNotAvailable       [6] NULL, -- EXPLICIT,
	callBarred          		[7] EXPLICIT	CallBarredParam,
	... 
    }

END
