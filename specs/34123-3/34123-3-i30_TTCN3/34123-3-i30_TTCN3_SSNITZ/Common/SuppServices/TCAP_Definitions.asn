TCAP-Definitions DEFINITIONS  ::=

BEGIN

IMPORTS  

  InvokeArgument,
  ReturnRes,
  ReturnErrPara,
  Lcs-MOLR-ErrPara

FROM TCAP-Definitions-Para;


--************************************************
-- From ITU-T Rec. X.880 (July/1994)
--************************************************

Code ::= CHOICE {
		local	INTEGER,
		global	OBJECT IDENTIFIER
		}
		

--********************************************************
-- Derived from ITU-T Rec. Q.773 (June/1997)
--********************************************************
Component ::= CHOICE {
			invoke				[1] IMPLICIT Invoke,
			returnResultLast	[2] IMPLICIT ReturnResult,
			returnError			[3] IMPLICIT ReturnError,
			reject				[4] IMPLICIT Reject 
			}
	-- The used part of Q.773 is almost the same as the component portion of TC messages. The only 
	-- difference is that returnResultNotLast is not used. (see 24.080, clause 3.6.1)

Invoke ::=	SEQUENCE {
			invokeID		InvokeIdType,
			linkedID		[0] IMPLICIT InvokeIdType OPTIONAL,
			operationCode		Code,
						-- local:116 for lcsNotification
						-- local:115 for lcs-MOLR

			parameter		InvokeArgument OPTIONAL 
			}


ReturnResult ::= SEQUENCE {
			invokeID		InvokeIdType,
			result			SEQUENCE {
				operationCode		Code,
							-- local:116 for lcsNotification
							-- local:115 for lcs-MOLR

				parameter				ReturnRes
												} OPTIONAL
			}


ReturnError ::=	SEQUENCE {
			invokeID		InvokeIdType,
			errorCode		Code,
			      		-- local:34 for SystemFailure
			      		-- local:36 for UnexpectedDataValue
			      		-- local:35 for DataMissing
			      		-- local:21 for FacilityNotSupported
			      		-- local:19 for SS-SubscriptionViolation
			      		-- local:54 for PositionMethodFailure
			      		
			parameter		ReturnErrPara OPTIONAL 
			}

Reject ::= SEQUENCE {
			invokeID CHOICE {
				derivable				InvokeIdType,
				not-derivable		NULL },
			problem CHOICE {
				generalProblem				[0] IMPLICIT GeneralProblem,
				invokeProblem				[1] IMPLICIT InvokeProblem,
				returnResultProblem	[2] IMPLICIT ReturnResultProblem,
				returnErrorProblem		[3] IMPLICIT ReturnErrorProblem } 
				}

InvokeIdType ::= INTEGER (-128..127)

GeneralProblem ::=	INTEGER {
					unrecognizedComponent (0),
					mistypedComponent (1),
					badlyStructuredComponent (2) }

InvokeProblem ::=	INTEGER {duplicateInvokeID (0),
					unrecognizedOperation (1),
					mistypedParameter (2),
					resourceLimitation (3),
					initiatingRelease (4),
					unrecognizedLinkedID (5),
					linkedResponseUnexpected (6),
					unexpectedLinkedOperation (7) }

ReturnResultProblem ::=	INTEGER {unrecognizedInvokeID (0),
				 returnResultUnexpected (1),
				 mistypedParameter (2) }

ReturnErrorProblem ::=	INTEGER {unrecognizedInvokeID (0),
				 returnErrorUnexpected (1),
				 unrecognizedError (2),
				 unexpectedError (3),
				 mistypedParameter (4) }
								


END
