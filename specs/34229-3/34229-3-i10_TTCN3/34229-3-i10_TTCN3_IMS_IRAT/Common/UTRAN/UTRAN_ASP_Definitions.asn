UTRAN-ASP-Definitions DEFINITIONS AUTOMATIC TAGS ::=
BEGIN

-- IMPORTs from RRC Type definitions

IMPORTS
  MCCH-Message,
  MSCH-Message,
  BCCH-BCH-Message,
  BCCH-FACH-Message,
  DL-CCCH-Message,
  DL-DCCH-Message,
  DL-SHCCH-Message,
  E-AGCH-DRX-Info-TDD128,
  PCCH-Message,
  UL-CCCH-Message,
  UL-DCCH-Message,
  UL-SHCCH-Message,
  DL-DCCH-MessageType,
  UL-DCCH-MessageType,
  DL-CCCH-MessageType,
  UL-CCCH-MessageType,
  PCCH-MessageType,
  DL-SHCCH-MessageType,
  UL-SHCCH-MessageType,
  BCCH-FACH-MessageType,
  MCCH-MessageType,
  MSCH-MessageType,
  ActiveSetUpdate,
  ActiveSetUpdate-r3-IEs,
  ActiveSetUpdate-v4b0ext-IEs,
  ActiveSetUpdate-v590ext-IEs,
  ActiveSetUpdate-v690ext-IEs,
  ActiveSetUpdate-r6-IEs,
  ActiveSetUpdate-v6b0ext-IEs,
  ActiveSetUpdateComplete,
  ActiveSetUpdateFailure,
  AssistanceDataDelivery,
  AssistanceDataDelivery-r3-IEs,
  AssistanceDataDelivery-v3a0ext,
  AssistanceDataDelivery-v4b0ext-IEs,
  CellChangeOrderFromUTRAN,
  CellChangeOrderFromUTRAN-r3-IEs,
  CellChangeOrderFromUTRAN-v590ext-IEs,
  CellChangeOrderFromUTRANFailure,
  CellChangeOrderFromUTRANFailure-r3-IEs,
  CellUpdate,
  CellUpdate-v590ext,
  CellUpdate-v690ext-IEs,
  CellUpdate-v6b0ext-IEs,
  CellUpdateConfirm,
  CellUpdateConfirm-r3-IEs,
  CellUpdateConfirm-v3a0ext,
  CellUpdateConfirm-v4b0ext-IEs,
  CellUpdateConfirm-v590ext-IEs,
  CellUpdateConfirm-v5d0ext-IEs,
  CellUpdateConfirm-r4-IEs,
  CellUpdateConfirm-r5-IEs,
  CellUpdateConfirm-r6-IEs,
  CellUpdateConfirm-v690ext-IEs,
  CellUpdateConfirm-v6b0ext-IEs,
  CellUpdateConfirm-CCCH,
  ControlChannelDRXInfo-TDD128-r8,
  CounterCheck,
  CounterCheck-r3-IEs,
  CounterCheckResponse,
  DownlinkDirectTransfer,
  DownlinkDirectTransfer-r3-IEs,
  HandoverToUTRANCommand,
  HandoverToUTRANCommand-r3-IEs,
  HandoverToUTRANCommand-r4-IEs,
  HandoverToUTRANCommand-r5-IEs,
  HandoverToUTRANCommand-r6-IEs,
  HandoverToUTRANCommand-v6b0ext-IEs,
  HandoverToUTRANComplete,
  InitialDirectTransfer,
  InitialDirectTransfer-v3a0ext,
  InitialDirectTransfer-v590ext,
  InitialDirectTransfer-v690ext-IEs,
  HandoverFromUTRANCommand-GSM,
  HandoverFromUTRANCommand-GSM-r3-IEs,
  HandoverFromUTRANCommand-GSM-r6-IEs,
  HandoverFromUTRANCommand-GSM-v690ext-IEs,
  HandoverFromUTRANCommand-GERANIu,
  HandoverFromUTRANCommand-GERANIu-r5-IEs,
  HandoverFromUTRANCommand-CDMA2000,
  HandoverFromUTRANCommand-CDMA2000-r3-IEs,
  HandoverFromUTRANFailure,
  HandoverFromUtranFailure-v590ext-IEs,
  InterRATHandoverInfo,
  InterRATHandoverInfo-v390ext-IEs,
  InterRATHandoverInfo-v3a0ext-IEs,
  InterRATHandoverInfo-v3d0ext-IEs,
  InterRATHandoverInfo-v3g0ext-IEs,
  InterRATHandoverInfo-r3-add-ext-IEs,
  InterRATHandoverInfo-v4b0ext-IEs,
  InterRATHandoverInfo-v4d0ext-IEs,
  InterRATHandoverInfo-v590ext-IEs,
  InterRATHandoverInfo-v690ext1-IEs,
  InterRATHandoverInfo-v690ext-IEs,
  InterRATHandoverInfo-v6b0ext-IEs,
  MeasurementControl,
  MeasurementControl-r3-IEs,
  MeasurementControl-v390ext,
  MeasurementControl-v3a0ext,
  MeasurementControl-r4-IEs,
  MeasurementControl-v590ext-IEs,
  MeasurementControl-v5b0ext-IEs,
  MeasurementControl-r6-IEs,
  MeasurementControl-v6a0ext-IEs,
  MeasurementControlFailure,
  MeasurementControlFailure-v590ext-IEs,
  MeasurementReport,
  MeasurementReport-v390ext,
  MeasurementReport-v4b0ext-IEs,
  MeasurementReport-v590ext-IEs,
  MeasurementReport-v5b0ext-IEs,
  MeasurementReport-v690ext-IEs,
  PagingType1,
  PagingType1-v590ext-IEs,
  PagingType2,
  PhysicalChannelReconfiguration,
  PhysicalChannelReconfiguration-r3-IEs,
  PhysicalChannelReconfiguration-v3a0ext,
  PhysicalChannelReconfiguration-v4b0ext-IEs,
  PhysicalChannelReconfiguration-v590ext-IEs,
  PhysicalChannelReconfiguration-r4-IEs,
  PhysicalChannelReconfiguration-r5-IEs,
  PhysicalChannelReconfiguration-r6-IEs,
  PhysicalChannelReconfiguration-v690ext-IEs,
  PhysicalChannelReconfiguration-v6b0ext-IEs,
  PhysicalChannelReconfigurationComplete,
  PhysicalChannelReconfigurationFailure,
  PhysicalSharedChannelAllocation,
  PhysicalSharedChannelAllocation-r3-IEs,
  PhysicalSharedChannelAllocation-r4-IEs,
  PhysicalSharedChannelAllocation-v690ext-IEs,
  PUSCHCapacityRequest,
  PUSCHCapacityRequest-v590ext,
  RadioBearerReconfiguration,
  RadioBearerReconfiguration-r3-IEs,
  RadioBearerReconfiguration-v3a0ext,
  RadioBearerReconfiguration-v4b0ext-IEs,
  RadioBearerReconfiguration-v590ext-IEs,
  RadioBearerReconfiguration-v5d0ext-IEs,
  RadioBearerReconfiguration-r4-IEs,
  RadioBearerReconfiguration-r5-IEs,
  RadioBearerReconfiguration-r6-IEs,
  RadioBearerReconfiguration-v690ext-IEs,
  RadioBearerReconfiguration-v6b0ext-IEs,
  RadioBearerReconfigurationComplete,
  RadioBearerReconfigurationFailure,
  RadioBearerRelease,
  RadioBearerRelease-r3-IEs,
  RadioBearerRelease-v3a0ext,
  RadioBearerRelease-v4b0ext-IEs,
  RadioBearerRelease-v590ext-IEs,
  RadioBearerRelease-r4-IEs,
  RadioBearerRelease-r5-IEs,
  RadioBearerRelease-v690ext-IEs,
  RadioBearerRelease-r6-IEs,
  RadioBearerRelease-v6b0ext-IEs,
  RadioBearerReleaseComplete,
  RadioBearerReleaseFailure,
  RadioBearerSetup,
  RadioBearerSetup-r3-IEs,
  RadioBearerSetup-v3a0ext,
  RadioBearerSetup-v4b0ext-IEs,
  RadioBearerSetup-v590ext-IEs,
  RadioBearerSetup-v5d0ext-IEs,
  RadioBearerSetup-r4-IEs,
  RadioBearerSetup-r5-IEs,
  RadioBearerSetup-v690ext-IEs,
  RadioBearerSetup-r6-IEs,
  RadioBearerSetup-v6b0ext-IEs,
  RadioBearerSetupComplete,
  RadioBearerSetupFailure,
  RRCConnectionReject,
  RRCConnectionReject-r3-IEs,
  RRCConnectionReject-v690ext-IEs,
  RRCConnectionRelease,
  RRCConnectionRelease-r3-IEs,
  RRCConnectionRelease-r4-IEs,
  RRCConnectionRelease-v690ext-IEs,
  RRCConnectionRelease-CCCH,
  RRCConnectionRelease-CCCH-r3-IEs,
  RRCConnectionRelease-CCCH-r4-IEs,
  RRCConnectionRelease-CCCH-r5-IEs,
  RRCConnectionRelease-CCCH-v690ext-IEs,
  RRCConnectionReleaseComplete,
  RRCConnectionRequest,
  RRCConnectionRequest-v3d0ext-IEs,
  RRCConnectionRequest-v4b0ext-IEs,
  RRCConnectionRequest-v590ext-IEs,
  RRCConnectionRequest-v690ext-IEs,
  RRCConnectionRequest-v6b0ext-IEs,
  RRCConnectionSetup,
  RRCConnectionSetup-r3-IEs,
  RRCConnectionSetup-v4b0ext-IEs,
  RRCConnectionSetup-v590ext-IEs,
  RRCConnectionSetup-r4-IEs,
  RRCConnectionSetup-r5-IEs,
  RRCConnectionSetup-v690ext-IEs,
  RRCConnectionSetup-r6-IEs,
  RRCConnectionSetup-v6b0ext-IEs,
  RRCConnectionSetupComplete,
  RRCConnectionSetupComplete-v370ext,
  RRCConnectionSetupComplete-v380ext-IEs,
  RRCConnectionSetupComplete-v3a0ext-IEs,
  RRCConnectionSetupComplete-v3g0ext-IEs,
  RRCConnectionSetupComplete-r3-add-ext-IEs,
  RRCConnectionSetupComplete-v4b0ext-IEs,
  RRCConnectionSetupComplete-v590ext-IEs,
  RRCConnectionSetupComplete-v5c0ext-IEs,
  RRCConnectionSetupComplete-v650ext-IEs,
  RRCConnectionSetupComplete-v680ext-IEs,
  RRCConnectionSetupComplete-v690ext-IEs,
  RRC-FailureInfo,
  RRC-FailureInfo-r3-IEs,
  RRCStatus,
  SecurityModeCommand,
  SecurityModeCommand-r3-IEs,
  SecurityModeComplete,
  SecurityModeFailure,
  SignallingConnectionRelease,
  SignallingConnectionRelease-r3-IEs,
  SignallingConnectionReleaseIndication,
  SystemInformation-BCH,
  SystemInformation-FACH,
  FirstSegment,
  FirstSegmentShort,
  SubsequentSegment,
  LastSegment,
  LastSegmentShort,
  CompleteSIB-List,
  CompleteSIB,
  CompleteSIBshort,
  SystemInformationChangeIndication,
  TransportChannelReconfiguration,
  TransportChannelReconfiguration-r3-IEs,
  TransportChannelReconfiguration-v3a0ext,
  TransportChannelReconfiguration-v4b0ext-IEs,
  TransportChannelReconfiguration-v590ext-IEs,
  TransportChannelReconfiguration-r4-IEs,
  TransportChannelReconfiguration-r5-IEs,
  TransportChannelReconfiguration-v690ext-IEs,
  TransportChannelReconfiguration-r6-IEs,
  TransportChannelReconfiguration-v6b0ext-IEs,
  TransportChannelReconfigurationComplete,
  TransportChannelReconfigurationFailure,
  TransportFormatCombinationControl,
  TransportFormatCombinationControlFailure,
  UECapabilityEnquiry,
  UECapabilityEnquiry-r3-IEs,
  UECapabilityEnquiry-v4b0ext-IEs,
  UECapabilityEnquiry-v590ext-IEs,
  UECapabilityInformation,
  UECapabilityInformation-v370ext,
  UECapabilityInformation-v380ext-IEs,
  UECapabilityInformation-v3a0ext-IEs,
  UECapabilityInformation-r3-add-ext-IEs,
  UECapabilityInformation-v4b0ext,
  UECapabilityInformation-v590ext,
  UECapabilityInformation-v5c0ext,
  UECapabilityInformation-v650ext-IEs,
  UECapabilityInformation-v680ext-IEs,
  UECapabilityInformation-v690ext-IEs,
  UECapabilityInformationConfirm,
  UECapabilityInformationConfirm-r3-IEs,
  UplinkDirectTransfer,
  UplinkDirectTransfer-v690ext-IEs,
  UplinkPhysicalChannelControl,
  UplinkPhysicalChannelControl-r3-IEs,
  UplinkPhysicalChannelControl-v4b0ext-IEs,
  UplinkPhysicalChannelControl-r4-IEs,
  UplinkPhysicalChannelControl-r5-IEs,
  UplinkPhysicalChannelControl-v690ext-IEs,
  UplinkPhysicalChannelControl-v6a0ext-IEs,
  URAUpdate,
  URAUpdateConfirm,
  URAUpdateConfirm-r3-IEs,
  URAUpdateConfirm-r5-IEs,
  URAUpdateConfirm-v690ext-IEs,
  URAUpdateConfirm-CCCH,
  URAUpdateConfirm-CCCH-r3-IEs,
  UTRANMobilityInformation,
  UTRANMobilityInformation-r3-IEs,
  UTRANMobilityInformation-v3a0ext-IEs,
  UTRANMobilityInformation-r5-IEs,
  UtranMobilityInformation-v690ext-IEs,
  UTRANMobilityInformationConfirm,
  UTRANMobilityInformationFailure,
  MBMSAccessInformation,
  MBMSCommonPTMRBInformation,
  MBMSCurrentCellPTMRBInformation,
  MBMSGeneralInformation,
  MBMSGeneralInformation-v6b0ext-IEs,
  MBMSModificationRequest,
  MBMSModificationRequest-v6b0ext-IEs,
  MBMSModifiedServicesInformation,
  MBMSNeighbouringCellPTMRBInformation,
  MBMSSchedulingInformation,
  MBMSUnmodifiedServicesInformation,
  MultiCarrier-HSDSCH-physical-layer-category,
  MultiCarrier-HSDSCH-physical-layer-category-extension,
  HS-SCCH-SystemInfo-TDD128,
  Ansi-41-IDNNS,
  CN-DomainIdentity,
  CN-DomainInformation,
  CN-DomainInformationFull,
  CN-DomainInformationList,
  CN-DomainInformationListFull,
  CN-DomainSysInfo,
  CN-DomainSysInfoList,
  CN-InformationInfo,
  CN-InformationInfo-r6,
  CN-InformationInfoFull,
  Digit,
  Gsm-map-IDNNS,
  IMEI,
  IMEI-Digit,
  IMSI-GSM-MAP,
  IntraDomainNasNodeSelector,
  LAI,
  MCC,
  MNC,
  MultiplePLMN-List-r6,
  NAS-Message,
  NAS-Synchronisation-Indicator,
  NAS-SystemInformationGSM-MAP,
  P-TMSI-GSM-MAP,
  PagingRecordTypeID,
  PLMN-Identity,
  PLMN-IdentityWithOptionalMCC-r6,
  PLMN-Type,
  RAB-Identity,
  RAI,
  RoutingAreaCode,
  RoutingParameter,
  TMSI-GSM-MAP,
  AccessClassBarred,
  AccessClassBarredList,
  AllowedIndicator,
  CellAccessRestriction,
  CellBarred,
  CellIdentity,
  CellIdentity-PerRL-List,
  CellSelectReselectInfoSIB-3-4,
  DomainSpecificAccessRestrictionForSharedNetwork-v670ext,
  DomainSpecificAccessRestrictionList-v670ext,
  DomainSpecificAccessRestrictionParam-v670ext,
  DomainSpecificAccessRestriction-v670ext,
  MapParameter,
  Mapping,
  Mapping-LCR-r4,
  MappingFunctionParameter,
  MappingFunctionParameterList,
  MappingFunctionType,
  MappingInfo,
  Q-Hyst-S,
  Q-Hyst-S-Fine,
  RAT,
  RAT-FDD-Info,
  RAT-FDD-InfoList,
  RAT-Identifier,
  RAT-TDD-Info,
  RAT-TDD-InfoList,
  ReservedIndicator,
  S-SearchQual,
  S-SearchRXLEV,
  SpeedDependentScalingFactor,
  T-Barred,
  T-Reselection-S,
  T-Reselection-S-Fine,
  TreselectionScalingFactor,
  UpperLimit,
  URA-Identity,
  URA-IdentityList,
  AccessStratumReleaseIndicator,
  ActivationTime,
  BackoffControlParams,
  C-RNTI,
  CapabilityUpdateRequirement,
  CapabilityUpdateRequirement-r4-ext,
  CapabilityUpdateRequirement-r4,
  CellUpdateCause,
  CellUpdateCause-ext,
  ChipRateCapability,
  CipheringAlgorithm,
  CipheringModeCommand,
  CipheringModeInfo,
  CipheringModeInfo-r7,
  CN-DRX-CycleLengthCoefficient,
  CN-PagedUE-Identity,
  CompressedModeMeasCapability,
  CompressedModeMeasCapability-LCR-r4,
  CompressedModeMeasCapabFDDList,
  CompressedModeMeasCapabFDDList2,
  CompressedModeMeasCapabFDDList-ext,
  CompressedModeMeasCapabFDD,
  CompressedModeMeasCapabFDD2,
  CompressedModeMeasCapabFDD-ext,
  CompressedModeMeasCapabTDDList,
  CompressedModeMeasCapabTDD,
  CompressedModeMeasCapabGSMList,
  CompressedModeMeasCapabGSM,
  CompressedModeMeasCapabMC,
  HS-DSCH-TBSizeTable,
  CPCH-Parameters,
  DL-CapabilityWithSimultaneousHS-DSCHConfig,
  DL-DPCCH-BER,
  DL-PhysChCapabilityFDD,
  DL-PhysChCapabilityFDD-v380ext,
  SupportOfDedicatedPilotsForChEstimation,
  DL-PhysChCapabilityTDD,
  DL-PhysChCapabilityTDD-LCR-r4,
  DL-TransChCapability,
  DRAC-SysInfo,
  DRAC-SysInfoList,
  DSCH-RNTI,
  DTX-Info,
  DelayRestrictionFlag,
  E-AGCH-Information-r8,
  E-DPDCH-Info-r7,
  E-DPDCH-Info-r8,
  E-RNTI,
  ESN-DS-41,
  EstablishmentCause,
  FailureCauseWithProtErr,
  FailureCauseWithProtErrTrId,
  GroupIdentityWithReleaseInformation,
  GroupReleaseInformation,
  GSM-Measurements,
  H-RNTI,
  HS-DSCH-PagingSystemInformation,
  HSDSCH-physical-layer-category,
  HSDSCH-physical-layer-category-ext,
  HSDSCH-physical-layer-category-ext2,
  HSDSCH-physical-layer-category-ext3,  
  HSDSCH-physical-layer-category-ext4,
  HSDSCH-physical-layer-category-ext5,
  HSDSCH-physical-layer-category-ext6,
  HSDSCH-physical-layer-category-ext7,
  HSDSCH-physical-layer-category-ext8,
  UESpecificBehaviourInformation1idle,
  UESpecificBehaviourInformation1interRAT,
  IMSI-and-ESN-DS-41,
  IMSI-DS-41,
  InitialPriorityDelayList,
  InitialUE-Identity,
  IntegrityCheckInfo,
  IntegrityProtActivationInfo,
  IntegrityProtectionAlgorithm,
  IntegrityProtectionModeCommand,
  IntegrityProtectionModeInfo,
  IntegrityProtectionModeInfo-r7,
  IntegrityProtInitNumber,
  MaxHcContextSpace,
  MaxHcContextSpace-r5-ext,
  MaxROHC-ContextSessions-r4,
  MaximumAM-EntityNumberRLC-Cap,
  MaximumBitRate,
  MaximumRLC-WindowSize,
  MaxNoDPDCH-BitsTransmitted,
  MaxNoBits,
  MaxNoPhysChBitsReceived,
  MaxNoSCCPCH-RL,
  MaxNumberOfTF,
  MaxNumberOfTFC-DL,
  MaxNumberOfTFC-UL,
  MaxPhysChPerFrame,
  MaxPhysChPerSubFrame-r4,
  MaxPhysChPerTimeslot,
  MaxPhysChPerTS,
  MaxSimultaneousCCTrCH-Count,
  MaxSimultaneousTransChsDL,
  MaxSimultaneousTransChsUL,
  MaxTransportBlocksDL,
  MaxTransportBlocksUL,
  MaxTS-PerFrame,
  MaxTS-PerSubFrame-r4,
  MeasurementCapability,
  MeasurementCapabilityExt,
  MeasurementCapabilityExt2,
  MeasurementCapability-r4-ext,
  MessageAuthenticationCode,
  MinimumSF-DL,
  MinimumSF-UL,
  MultiModeCapability,
  MultiRAT-Capability,
  MultiModeRAT-Capability-v590ext,
  MultiModeRAT-Capability-v680ext,
  N-300,
  N-301,
  N-302,
  N-304,
  N-308,
  N-310,
  N-312,
  N-312ext,
  N-312-r5,
  N-313,
  N-315,
  N-315ext,
  N-315-r5,
  N-AccessFails,
  N-AP-RetransMax,
  NetworkAssistedGPS-Supported,
  NF-BO-AllBusy,
  NF-BO-NoAICH,
  NF-BO-Mismatch,
  NS-BO-Busy,
  NS-IP,
  P-TMSI-and-RAI-GSM-MAP,
  PagingCause,
  PagingRecord,
  PagingRecord2-r5,
  PagingRecordList,
  PagingRecord2List-r5,
  PDCP-Capability,
  PDCP-Capability-r4-ext,
  PDCP-Capability-r5-ext,
  PDCP-Capability-r5-ext2,
  PhysicalChannelCapability,
  PhysicalChannelCapability-LCR-r4,
  PhysicalChannelCapability-hspdsch-r5,
  PNBSCH-Allocation-r4,
  ProtocolErrorCause,
  ProtocolErrorIndicator,
  ProtocolErrorIndicatorWithMoreInfo,
  ProtocolErrorMoreInformation,
  RadioFrequencyBandFDD,
  RadioFrequencyBandFDD2,
  RadioFrequencyBandFDD3,
  RadioFrequencyBandTDDList,
  RadioFrequencyBandTDD,
  RadioFrequencyBandGSM,
  Rb-timer-indicator,
  Re-EstablishmentTimer,
  RedirectionInfo,
  RedirectionInfo-r6,
  RejectionCause,
  ReleaseCause,
  RF-Capability,
  RF-Capability-r4-ext,
  RLC-Capability,
  RLC-Capability-r5-ext,
  RRC-ConnectionReleaseInformation,
  RRC-MessageSequenceNumber,
  RRC-MessageSequenceNumberList,
  RRC-StateIndicator,
  RRC-TransactionIdentifier,
  S-RNTI,
  S-RNTI-2,
  SecurityCapability,
  Serving-HSDSCH-CellInformation,
  SimultaneousSCCPCH-DPCH-Reception,
  SRNC-Identity,
  START-Value,
  STARTList,
  STARTSingle,
  CapabilityUpdateRequirement-r5,
  SystemSpecificCapUpdateReq,
  SystemSpecificCapUpdateReq-v590ext,
  SystemSpecificCapUpdateReq-r5,
  SystemSpecificCapUpdateReqList,
  SystemSpecificCapUpdateReqList-r5,
  T-300,
  T-301,
  T-302,
  T-304,
  T-305,
  T-307,
  T-308,
  T-309,
  T-310,
  T-311,
  T-312,
  T-313,
  T-314,
  T-315,
  T-316,
  T-317,
  T-318,
  T-CPCH,
  TMSI-and-LAI-GSM-MAP,
  TMSI-DS-41,
  TotalRLC-AM-BufferSize,
  TotalRLC-AM-BufferSize-r5-ext,
  TransmissionProbability,
  TransportChannelCapability,
  TurboSupport,
  TxRxFrequencySeparation,
  U-RNTI,
  U-RNTI-Group,
  U-RNTI-Short,
  UE-CapabilityContainer-IEs,
  UE-RadioAccessCapability-v6b0ext-IEs,
  UE-ConnTimersAndConstants,
  UE-ConnTimersAndConstants-v3a0ext,
  UE-ConnTimersAndConstants-r5,
  UE-HSPA-Identities-r6,
  UE-IdleTimersAndConstants,
  UE-IdleTimersAndConstants-v3a0ext,
  UE-MultiModeRAT-Capability,
  UE-PowerClass,
  UE-PowerClassExt,
  UE-RadioAccessCapability,
  UE-RadioAccessCapabilityInfo,
  UE-RadioAccessCapability-v370ext,
  UE-RadioAccessCapability-v380ext,
  UE-RadioAccessCapability-v3a0ext,
  UE-RadioAccessCapability-v3g0ext,
  UE-RadioAccessCapability-v650ext,
  UE-RadioAccessCapability-v690ext,
  UE-RadioAccessCapabBandFDDList2,
  UE-RadioAccessCapabBandFDD2,
  UE-PositioningCapabilityExt-v380,
  UE-PositioningCapabilityExt-v3a0,
  UE-PositioningCapabilityExt-v3g0,
  UE-RadioAccessCapabBandFDDList,
  UE-RadioAccessCapabBandFDDList-ext,
  UE-RadioAccessCapabBandFDD,
  UE-RadioAccessCapabBandFDD-ext,
  UE-RadioAccessCapability-v4b0ext,
  UE-RadioAccessCapabilityComp,
  UE-RadioAccessCapabilityComp-ext,
  UE-RadioAccessCapabilityComp2,
  RF-CapabilityComp,
  RF-CapabBandFDDComp,
  RF-CapabBandListFDDComp,
  RF-CapabBandListFDDComp-ext,
  UE-RadioAccessCapability-v590ext,
  UE-RadioAccessCapability-v5c0ext,
  UE-RadioAccessCapability-v680ext,
  UL-PhysChCapabilityFDD,
  UL-PhysChCapabilityFDD-r6,
  UL-PhysChCapabilityTDD,
  UL-PhysChCapabilityTDD-LCR-r4,
  PhysicalChannelCapability-edch-r6,
  UL-TransChCapability,
  UE-Positioning-Capability,
  UE-SecurityInformation,
  UE-SecurityInformation2,
  URA-UpdateCause,
  UTRAN-DRX-CycleLengthCoefficient,
  UpPCHposition-LCR,
  WaitTime,
  AlgorithmSpecificInfo,
  AlgorithmSpecificInfo-r4,
  CID-InclusionInfo-r4,
  COUNT-C,
  COUNT-C-MSB,
  DefaultConfigIdentity,
  DefaultConfigIdentity-r4,
  DefaultConfigIdentity-r5,
  DefaultConfigIdentity-r6,
  DefaultConfigMode,
  DDI,
  DL-AM-RLC-Mode,
  DL-AM-RLC-Mode-r5,
  DL-CounterSynchronisationInfo,
  DL-CounterSynchronisationInfo-r5,
  DL-LogicalChannelMapping,
  DL-LogicalChannelMapping-r5,
  DL-LogicalChannelMappingList,
  DL-LogicalChannelMappingList-r5,
  DL-Reception-Window-Size-r6,
  DL-RFC3095-r4,
  DL-RLC-Mode,
  DL-RLC-Mode-r5,
  DL-RLC-Mode-r6,
  DL-RLC-Mode-r7,
  DL-RLC-Mode-r11,
  DL-RLC-StatusInfo,
  DL-TM-RLC-Mode,
  DL-TransportChannelType,
  DL-TransportChannelType-r5,
  DL-UM-RLC-LI-size,
  DL-UM-RLC-Mode-r5,
  DL-UM-RLC-Mode-r6,
  E-TFCS-Info,
  ExpectReordering,
  ExplicitDiscard,
  HeaderCompressionInfo,
  HeaderCompressionInfoList,
  HeaderCompressionInfo-r4,
  HeaderCompressionInfoList-r4,
  LogicalChannelIdentity,
  LosslessSRNS-RelocSupport,
  MAC-d-HFN-initial-value,
  MAC-DTX-Cycle-2ms,
  MAC-DTX-Cycle-10ms,
  MAC-ehs-AddReconfReordQ,
  MAC-ehs-AddReconfReordQ-r9,
  MAC-ehs-AddReconfReordQ-r11,
  MAC-ehs-QueueId,
  MAC-InactivityThreshold,
  MAC-LogicalChannelPriority,
  MaxDAT,
  MaxDAT-Retransmissions,
  MaxMRW,
  MaxPDCP-SN-WindowSize,
  MaxRST,
  NewTiming,
  NoExplicitDiscard,
  PDCP-Info,
  PDCP-Info-r4,
  PDCP-InfoReconfig,
  PDCP-InfoReconfig-r4,
  PDCP-PDU-Header,
  PDCP-ROHC-TargetMode,
  PDCP-SN-Info,
  Poll-PDU,
  Poll-SDU,
  PollingInfo,
  PollWindow,
  PowerControlGAP,
  PredefinedConfigIdentity,
  PredefinedConfigValueTag,
  PredefinedRB-Configuration,
  PreDefRadioConfiguration,
  PredefinedConfigStatusList,
  PredefinedConfigStatusInfo,
  PredefinedConfigStatusListComp,
  PredefinedConfigSetsWithDifferentValueTag,
  PredefinedConfigSetWithDifferentValueTag,
  PredefinedConfigValueTagList,
  PredefinedConfigStatusListVarSz,
  RAB-Info,
  RAB-Info-r6-ext,
  RAB-Info-v6b0ext,
  RAB-Info-r6,
  RAB-InformationList,
  RAB-InformationList-r6,
  RAB-InformationReconfigList,
  RAB-InformationReconfig,
  RAB-Info-Post,
  RAB-InformationSetup,
  RAB-InformationSetup-r4,
  RAB-InformationSetup-r5,
  RAB-InformationSetup-r6-ext,
  RAB-InformationSetup-r6,
  RAB-InformationSetup-v6b0ext,
  RAB-InformationSetupList,
  RAB-InformationSetupList-r4,
  RAB-InformationSetupList-r5,
  RAB-InformationSetupList-r6,
  RAB-InformationSetupList-r6-ext,
  RAB-InformationSetupList-v6b0ext,
  RB-ActivationTimeInfo,
  RB-ActivationTimeInfoList,
  RB-COUNT-C-Information,
  RB-COUNT-C-InformationList,
  RB-COUNT-C-MSB-Information,
  RB-COUNT-C-MSB-InformationList,
  RB-Identity,
  RB-IdentityList,
  RB-InformationAffected,
  RB-InformationAffected-r5,
  RB-InformationAffected-r6,
  RB-InformationAffectedList,
  RB-InformationAffectedList-r5,
  RB-InformationAffectedList-r6,
  RB-InformationChanged-r6,
  RB-InformationChangedList-r6,
  RB-InformationReconfig,
  RB-InformationReconfig-r4,
  RB-InformationReconfig-r5,
  RB-InformationReconfig-r6,
  RB-InformationReconfigList,
  RB-InformationReconfigList-r4,
  RB-InformationReconfigList-r5,
  RB-InformationReconfigList-r6,
  RB-InformationReleaseList,
  RB-InformationSetup,
  RB-InformationSetup-r4,
  RB-InformationSetup-r5,
  RB-InformationSetup-r6,
  RB-InformationSetupList,
  RB-InformationSetupList-r4,
  RB-InformationSetupList-r5,
  RB-InformationSetupList-r6,
  RB-MappingInfo,
  RB-MappingInfo-r5,
  RB-MappingInfo-r6,
  RB-MappingOption,
  RB-MappingOption-r5,
  RB-MappingOption-r6,
  RB-PDCPContextRelocation,
  RB-PDCPContextRelocationList,
  RB-StopContinue,
  RB-WithPDCP-Info,
  RB-WithPDCP-InfoList,
  ReceivingWindowSize,
  RFC2507-Info,
  RFC3095-Info-r4,
  RLC-Info,
  RLC-Info-r5,
  RLC-Info-r6,
  RLC-Info-MCCH-r6,
  RLC-Info-MSCH-r6,
  RLC-Info-MTCH-r6,
  RLC-InfoChoice,
  RLC-InfoChoice-r5,
  RLC-InfoChoice-r6,
  RLC-PDU-Size,
  RLC-PDU-SizeList,
  RLC-SequenceNumber,
  RLC-SizeInfo,
  RLC-SizeExplicitList,
  ROHC-Profile-r4,
  ROHC-ProfileList-r4,
  ROHC-PacketSize-r4,
  ROHC-PacketSizeList-r4,
  SRB-InformationSetup,
  SRB-InformationSetup-r5,
  SRB-InformationSetup-r6,
  SRB-InformationSetupList,
  SRB-InformationSetupList-r5,
  SRB-InformationSetupList-r6,
  SRB-InformationSetupList2,
  SRB-InformationSetupList2-r6,
  TimerDAR-r6,
  TimerDiscard,
  TimerEPC,
  TimerMRW,
  TimerOSD-r6,
  TimerPoll,
  TimerPollPeriodic,
  TimerPollProhibit,
  TimerRST,
  TimerStatusPeriodic,
  TimerStatusProhibit,
  TransmissionRLC-Discard,
  TransmissionWindowSize,
  UL-AM-RLC-Mode,
  UL-CounterSynchronisationInfo,
  UL-LogicalChannelMapping,
  UL-LogicalChannelMapping-r6,
  UL-LogicalChannelMappingList,
  UL-LogicalChannelMappingList-r6,
  UL-LogicalChannelMappings,
  UL-LogicalChannelMappings-r6,
  UL-RFC3095-r4,
  UL-RLC-Mode,
  UL-TM-RLC-Mode,
  UL-UM-RLC-Mode,
  UL-TransportChannelType,
  UM-RLC-DuplAvoid-Reord-Info-r6,
  UM-RLC-OutOSeqDelivery-Info-r6,
  WindowSizeDAR-r6,
  WindowSizeOSD-r6,
  AddOrReconfMAC-dFlow,
  AllowedTFC-List,
  AllowedTFI-List,
  BitModeRLC-SizeInfo,
  BLER-QualityValue,
  ChannelCodingType,
  CodingRate,
  CommonDynamicTF-Info,
  CommonDynamicTF-Info-DynamicTTI,
  CommonDynamicTF-InfoList,
  CommonDynamicTF-InfoList-DynamicTTI,
  CommonTransChTFS,
  CommonTransChTFS-LCR,
  CPCH-SetID,
  CRC-Size,
  DedicatedDynamicTF-Info,
  DedicatedDynamicTF-Info-DynamicTTI,
  DedicatedDynamicTF-InfoList,
  DedicatedDynamicTF-InfoList-DynamicTTI,
  DedicatedTransChTFS,
  DL-AddReconfTransChInfo2List,
  DL-AddReconfTransChInfoList,
  DL-AddReconfTransChInfoList-r4,
  DL-AddReconfTransChInfoList-r5,
  DL-AddReconfTransChInformation,
  DL-AddReconfTransChInformation-r4,
  DL-AddReconfTransChInformation-r5,
  DL-AddReconfTransChInformation2,
  DL-CommonTransChInfo,
  DL-CommonTransChInfo-r4,
  DL-DeletedTransChInfoList,
  DL-DeletedTransChInfoList-r5,
  DL-TransportChannelIdentity,
  DL-TransportChannelIdentity-r5,
  DL-TrCH-Type,
  DL-TrCH-TypeId1-r5,
  DL-TrCH-TypeId2-r5,
  DRAC-ClassIdentity,
  DRAC-StaticInformation,
  DRAC-StaticInformationList,
  E-DCH-AddReconf-MAC-d-Flow,
  E-DCH-AddReconf-MAC-d-FlowList,
  E-DCH-AddReconf-MAC-d-FlowList-r7,
  E-DCH-MAC-d-FlowIdentity,
  E-DCH-MAC-d-FlowMaxRetrans,
  E-DCH-MAC-d-FlowMultiplexingList,
  E-DCH-MAC-d-FlowPowerOffset,
  Common-E-DCH-MAC-d-FlowList,
  E-DCH-TTI,
  ExplicitTFCS-Configuration,
  GainFactor,
  GainFactorInformation,
  HSDSCH-Info,
  HARQ-Info,
  HARQ-Info-r7,
  HARQ-Info-r11,
  HARQ-Info-r13,
  HARQMemorySize,
  IndividualDL-CCTrCH-Info,
  IndividualDL-CCTrCH-InfoList,
  IndividualUL-CCTrCH-Info,
  IndividualUL-CCTrCH-InfoList,
  LogicalChannelByRB,
  LogicalChannelList,
  MAC-d-FlowIdentityDCHandHSDSCH,
  MAC-d-FlowIdentity,
  MAC-d-PDU-SizeInfo-List,
  MAC-d-PDUsizeInfo,
  MAC-hs-AddReconfQueue-List,
  MAC-hs-AddReconfQueue,
  MAC-hs-DelQueue-List,
  MAC-hs-DelQueue,
  MAC-hs-WindowSize,
  NumberOfTbSizeAndTTIList,
  MessType,
  Non-allowedTFC-List,
  NumberOfTransportBlocks,
  OctetModeRLC-SizeInfoType1,
  OctetModeRLC-SizeInfoType2,
  PowerOffsetInfoShort,
  PowerOffsetInformation,
  PowerOffsetPp-m,
  PreDefTransChConfiguration,
  QualityTarget,
  RateMatchingAttribute,
  ReferenceTFC-ID,
  RestrictedTrChInfo,
  RestrictedTrChInfoList,
  SemistaticTF-Information,
  SignalledGainFactors,
  SplitTFCI-Signalling,
  SplitType,
  T1-ReleaseTimer,
  TFC-Subset,
  TFC-SubsetList,
  TFC-Value,
  TFCI-Field2-Information,
  TFCI-Range,
  TFCI-RangeList,
  TFCS,
  TFCS-Identity,
  TFCS-IdentityPlain,
  TFCS-InfoForDSCH,
  TFCS-ReconfAdd,
  TFCS-Removal,
  TFCS-RemovalList,
  TimeDurationBeforeRetry,
  TM-SignallingInfo,
  TransmissionTimeInterval,
  TransmissionTimeValidity,
  TransportChannelIdentity,
  TransportChannelIdentityDCHandDSCH,
  TransportFormatSet,
  TransportFormatSet-LCR,
  UL-AddReconfTransChInfoList,
  UL-AddReconfTransChInfoList-r6,
  UL-AddReconfTransChInformation,
  UL-AddReconfTransChInformation-r6,
  UL-CommonTransChInfo,
  UL-CommonTransChInfo-r4,
  UL-ControlledTrChList,
  UL-DeletedTransChInfoList,
  UL-DeletedTransChInfoList-r6,
  UL-TransportChannelIdentity,
  UL-TransportChannelIdentity-r6,
  UL-TrCH-Type,
  USCH-TransportChannelsInfo,
  ACK-NACK-repetitionFactor,
  AC-To-ASC-Mapping,
  AC-To-ASC-MappingTable,
  AccessServiceClass-FDD,
  AccessServiceClass-TDD,
  AccessServiceClass-TDD-LCR-r4,
  AdditionalPRACH-TF-and-TFCS-CCCH-IEs,
  AdditionalPRACH-TF-and-TFCS-CCCH,
  AdditionalPRACH-TF-and-TFCS-CCCH-List,
  AICH-Info,
  AICH-PowerOffset,
  AICH-TransmissionTiming,
  AllocationPeriodInfo,
  Alpha,
  AP-AICH-ChannelisationCode,
  AP-PreambleScramblingCode,
  AP-Signature,
  AP-Signature-VCAM,
  AP-Subchannel,
  ASCSetting-FDD,
  ASCSetting-TDD,
  ASCSetting-TDD-LCR-r4,
  AvailableAP-Signature-VCAMList,
  AvailableAP-SignatureList,
  AvailableAP-SubchannelList,
  AvailableMinimumSF-ListVCAM,
  AvailableMinimumSF-VCAM,
  AvailableSignatures,
  AvailableSubChannelNumbers,
  BEACON-PL-Est,
  BurstType,
  Bler-Target,
  CCTrCH-PowerControlInfo,
  CCTrCH-PowerControlInfo-r4,
  CCTrCH-PowerControlInfo-r5,
  CD-AccessSlotSubchannel,
  CD-AccessSlotSubchannelList,
  CD-CA-ICH-ChannelisationCode,
  CD-PreambleScramblingCode,
  CD-SignatureCode,
  CD-SignatureCodeList,
  CellAndChannelIdentity,
  CellParametersID,
  Cfntargetsfnframeoffset,
  ChannelAssignmentActive,
  ChannelisationCode256,
  ChannelReqParamsForUCSM,
  ClosedLoopTimingAdjMode,
  CodeNumberDSCH,
  CodeRange,
  CodeWordSet,
  CommonTimeslotInfo,
  CommonTimeslotInfoMBMS,
  CommonTimeslotInfoSCCPCH,
  Common-MAC-ehs-ReorderingQueue,
  ConstantValue,
  ConstantValueTdd,
  CPCH-PersistenceLevels,
  CPCH-PersistenceLevelsList,
  CPCH-SetInfo,
  CPCH-SetInfoList,
  CPCH-StatusIndicationMode,
  CQI-RepetitionFactor,
  CSICH-PowerOffset,
  DefaultDPCH-OffsetValueFDD,
  DefaultDPCH-OffsetValueTDD,
  DeltaPp-m,
  DeltaCQI,
  DeltaNACK,
  DeltaACK,
  DeltaSIR,
  DHS-Sync,
  DL-CCTrCh,
  DL-CCTrCh-r4,
  DL-CCTrChList,
  DL-CCTrChList-r4,
  DL-CCTrChListToRemove,
  DL-ChannelisationCode,
  DL-ChannelisationCodeList,
  DL-CommonInformation,
  DL-CommonInformation-r4,
  DL-CommonInformation-r5,
  DL-CommonInformation-r6,
  DL-CommonInformation-r7,
  DL-CommonInformation-r8,
  DL-CommonInformation-r10,
  DL-CommonInformation-r11,
  DL-CommonInformationPost,
  DL-CommonInformationPredef,
  DL-CompressedModeMethod,
  DL-DPCH-InfoCommon,
  DL-DPCH-InfoCommon-r4,
  DL-DPCH-InfoCommon-r6,
  DL-DPCH-InfoCommonPost,
  DL-DPCH-InfoCommonPredef,
  DL-DPCH-InfoPerRL,
  DL-DPCH-InfoPerRL-r4,
  DL-DPCH-InfoPerRL-r5,
  DL-DPCH-InfoPerRL-r6,
  DL-DPCH-InfoPerRL-r7,
  DL-FDPCH-InfoPerRL-r6,
  DL-FDPCH-InfoPerRL-r7,
  DL-FDPCH-InfoPerRL-r13,
  DL-DPCH-InfoPerRL-PostFDD,
  DL-DPCH-InfoPerRL-PostTDD,
  DL-DPCH-InfoPerRL-PostTDD-LCR-r4,
  DL-DPCH-PowerControlInfo,
  DL-FDPCH-InfoCommon-r6,
  DL-FrameType,
  DL-HSPDSCH-Information,
  DL-HSPDSCH-Information-r6,
  DL-HSPDSCH-Information-r7,
  DL-HSPDSCH-Information-r8,
  DL-HSPDSCH-Information-r9,
  DL-HSPDSCH-Information-r11,
  DL-HSPDSCH-TS-Configuration,
  DL-InformationPerRL,
  DL-InformationPerRL-r4,
  DL-InformationPerRL-r5,
  DL-InformationPerRL-r5bis,
  DL-InformationPerRL-r6,
  DL-InformationPerRL-v6b0ext,
  DL-InformationPerRL-List,
  DL-InformationPerRL-List-r4,
  DL-InformationPerRL-List-r5,
  DL-InformationPerRL-List-r6,
  DL-InformationPerRL-List-v6b0ext,
  DL-InformationPerRL-List-r5bis,
  DL-InformationPerRL-ListPostFDD,
  DL-InformationPerRL-PostFDD,
  DL-InformationPerRL-PostTDD,
  DL-InformationPerRL-PostTDD-LCR-r4,
  DL-PDSCH-Information,
  Dl-rate-matching-restriction,
  DL-TPC-PowerOffsetPerRL,
  DL-TPC-PowerOffsetPerRL-List,
  DL-TS-ChannelisationCode,
  DL-TS-ChannelisationCodesShort,
  DownlinkAdditionalTimeslots,
  DownlinkAdditionalTimeslots-LCR-r4,
  DownlinkTimeslotsCodes,
  DownlinkTimeslotsCodes-LCR-r4,
  DPC-Mode,
  DPCCH-PowerOffset,
  DPCCH-PowerOffset2,
  DPCH-CompressedModeInfo,
  DPCH-CompressedModeStatusInfo,
  DPCH-FrameOffset,
  DSCH-Mapping,
  DSCH-MappingList,
  DSCH-RadioLinkIdentifier,
  DSCH-TransportChannelsInfo,
  DTX-DRX-TimingInfo-r7,
  DurationTimeInfo,
  DynamicPersistenceLevel,
  DynamicPersistenceLevelList,
  DynamicPersistenceLevelTF-List,
  DynamicTFInformationCCCH,
  E-AGCH-ChannelisationCode,
  E-AGCH-Information,
  E-AGCH-Information-r7,
  E-DCH-MinimumSet-E-TFCI,
  E-DCH-ReconfigurationInfo,
  E-DCH-RL-InfoNewServingCell,
  E-DCH-RL-InfoOtherCell,  
  E-DPCCH-Info,
  E-DPCCH-Info-r7,
  E-DPCCH-DPCCH-PowerOffset,
  E-DPDCH-Info,
  E-DPDCH-PeriodicyOfSchedInfo,
  E-DPDCH-PL-NonMax,
  E-DPDCH-Reference-E-TFCI,
  E-DPDCH-Reference-E-TFCIList,
  E-DPDCH-SchedulingInfoConfiguration,
  E-DPDCH-SchedulingTransmConfiguration,
  E-DPDCH-MaxChannelisationCodes,
  E-HICH-ChannelisationCode,
  E-HICH-Information,
  E-HICH-Information-r11,
  E-HICH-Information-CommonEdch,
  E-HICH-Information-LCR, 
  E-HICH-RGCH-SignatureSequence,
  E-RGCH-CombinationIndex,
  E-RGCH-Information,
  E-RGCH-Information-CommonEdch,
  E-RUCCH-Info,
  E-TFCI-TableIndex,
  FACH-PCH-Information,
  FACH-PCH-InformationList,
  Feedback-cycle,
  FPACH-Info-r4,
  FrequencyInfo,
  FrequencyInfoFDD,
  FrequencyInfoTDD,
  HappyBit-DelayCondition,
  HARQ-Preamble-Mode,
  HS-ChannelisationCode-LCR,
  HS-PDSCH-Midamble-Configuration-TDD128,
  HS-DSCH-PagingSystemInformation-TDD128,
  HS-DSCH-DrxCellfach-info-TDD128,
  HS-SCCH-Info,
  HS-SCCH-Info-r6,
  HS-SCCH-Codes,
  HS-SCCH-LessInfo-r7,
  HS-SCCH-TDD128,
  HS-SCCH-TDD128-r6,
  HS-SICH-Configuration-TDD128,
  HS-SICH-Configuration-TDD128-r6,
  HS-SCCH-TDD384,
  HS-SCCH-TDD384-r6,
  HS-SICH-Configuration-TDD384,
  HS-SICH-Power-Control-Info-TDD384,
  HS-SCCH-SystemInfo,
  IndividualTimeslotInfo,
  IndividualTimeslotInfo-LCR-r4,
  IndividualTimeslotInfo-LCR-r4-ext,
  IndividualTS-Interference,
  IndividualTS-InterferenceList,
  ITP,
  NidentifyAbort,
  MaxAllowedUL-TX-Power,
  MaxAvailablePCPCH-Number,
  MaxPowerIncrease-r4,
  MaxTFCI-Field2Value,
  Measurement-Feedback-Info,
  MidambleConfigurationBurstType1and3,
  MidambleConfigurationBurstType2,
  MidambleShiftAndBurstType,
  MidambleShiftAndBurstType-DL,
  MidambleShiftAndBurstType-LCR-r4,
  MidambleShiftLong,
  MidambleShiftShort,
  MinimumSpreadingFactor,
  MultiCodeInfo,
  N-EOT,
  N-GAP,
  N-PCH,
  N-StartMessage,
  NB01,
  NF-Max,
  NumberOfDPDCH,
  NumberOfFBI-Bits,
  OpenLoopPowerControl-TDD,
  OpenLoopPowerControl-IPDL-TDD-r4,
  PagingIndicatorLength,
  PC-Preamble,
  PCP-Length,
  PCPCH-ChannelInfo,
  PCPCH-ChannelInfoList,
  PCPICH-UsageForChannelEst,
  PDSCH-CapacityAllocationInfo,
  PDSCH-CapacityAllocationInfo-r4,
  PDSCH-CodeInfo,
  PDSCH-CodeInfoList,
  PDSCH-CodeMap,
  PDSCH-CodeMapList,
  PDSCH-CodeMapping,
  PDSCH-Identity,
  PDSCH-Info,
  PDSCH-Info-r4,
  PDSCH-Info-LCR-r4,
  PDSCH-PowerControlInfo,
  PDSCH-SHO-DCH-Info,
  PDSCH-SysInfo,
  PDSCH-SysInfo-HCR-r5,
  PDSCH-SysInfo-LCR-r4,
  PDSCH-SysInfoList,
  PDSCH-SysInfoList-HCR-r5,
  PDSCH-SysInfoList-LCR-r4,
  PDSCH-SysInfoList-SFN,
  PDSCH-SysInfoList-SFN-HCR-r5,
  PDSCH-SysInfoList-SFN-LCR-r4,
  PersistenceScalingFactor,
  PersistenceScalingFactorList,
  PI-CountPerFrame,
  PichChannelisationCodeList-LCR-r4,
  PICH-Info,
  PICH-Info-LCR-r4,
  PICH-PowerOffset,
  PilotBits128,
  PilotBits256,
  MeasurementPowerOffset,
  PositionFixedOrFlexible,
  PowerControlAlgorithm,
  PowerOffsetPilot-pdpdch,
  PowerOffsetTPC-pdpdch,
  PowerRampStep,
  PRACH-ChanCodes-LCR-r4,
  PRACH-Definition-LCR-r4,
  PRACH-Midamble,
  PRACH-Partitioning,
  PRACH-Partitioning-LCR-r4,
  PRACH-PowerOffset,
  PRACH-RACH-Info,
  PRACH-RACH-Info-LCR-r4,
  PRACH-SystemInformation,
  PRACH-SystemInformation-LCR-r4,
  PRACH-SystemInformationList,
  PRACH-SystemInformationList-LCR-r4,
  PreambleRetransMax,
  PreambleScramblingCodeWordNumber,
  PreDefPhyChConfiguration,
  PrimaryCCPCH-Info,
  PrimaryCCPCH-Info-r4,
  PrimaryCCPCH-Info-LCR-r4,
  PrimaryCCPCH-Info-LCR-r4-ext,
  PrimaryCCPCH-InfoPost,
  PrimaryCCPCH-InfoPostTDD-LCR-r4,
  PrimaryCCPCH-TX-Power,
  PrimaryCPICH-Info,
  PrimaryCPICH-TX-Power,
  PrimaryScramblingCode,
  PuncturingLimit,
  PUSCH-CapacityAllocationInfo,
  PUSCH-CapacityAllocationInfo-r4,
  PUSCH-Identity,
  PUSCH-Info,
  PUSCH-Info-r4,
  PUSCH-Info-LCR-r4,
  PUSCH-PowerControlInfo-r4,
  PUSCH-SysInfo,
  PUSCH-SysInfo-HCR-r5,
  PUSCH-SysInfo-LCR-r4,
  PUSCH-SysInfoList,
  PUSCH-SysInfoList-HCR-r5,
  PUSCH-SysInfoList-LCR-r4,
  PUSCH-SysInfoList-SFN,
  PUSCH-SysInfoList-SFN-HCR-r5,
  PUSCH-SysInfoList-SFN-LCR-r4,
  RACH-TransmissionParameters,
  ReducedScramblingCodeNumber,
  RepetitionPeriodAndLength,
  RepetitionPeriodLengthAndOffset,
  ReplacedPDSCH-CodeInfo,
  ReplacedPDSCH-CodeInfoList,
  RepPerLengthOffset-PICH,
  RepPerLengthOffset-MICH,
  RestrictedTrCH,
  RestrictedTrCH-InfoList,
  RL-AdditionInformation,
  RL-AdditionInformation-r6,
  RL-AdditionInformation-v6b0ext,
  RL-AdditionInformationList,
  RL-AdditionInformationList-r6,
  RL-AdditionInformation-list-v6b0ext,
  RL-IdentifierList,
  RL-RemovalInformationList,
  RPP,
  S-Field,
  SCCPCH-ChannelisationCode,
  SCCPCH-ChannelisationCodeList,
  SCCPCH-InfoForFACH,
  SCCPCH-InfoForFACH-r4,
  SCCPCH-SystemInformation,
  SCCPCH-SystemInformation-LCR-r4-ext,
  SCCPCH-SystemInformationList,
  SCCPCH-SystemInformationList-LCR-r4-ext,
  SCCPCH-SystemInformation-MBMS-r6,
  ScramblingCodeChange,
  ScramblingCodeType,
  SecondaryCCPCH-Info,
  SecondaryCCPCH-Info-r4,
  SecondaryCCPCH-Info-LCR-r4-ext,
  SecondaryCCPCHInfo-MBMS-r6,
  SecondaryCPICH-Info,
  SecondaryScramblingCode,
  SecondInterleavingMode,
  SF256-AndCodeNumber,
  SF512-AndCodeNumber,
  SF512-AndPilot,
  SF-PDSCH,
  SF-PRACH,
  SFN-TimeInfo,
  SpecialBurstScheduling,
  SpreadingFactor,
  SRB-delay,
  SSDT-CellIdentity,
  SSDT-Information,
  SSDT-Information-r4,
  SSDT-UL,
  STTDIndication,
  SynchronisationParameters-r4,
  SYNC-UL-Procedure-r4,
  SYNC-UL-Info-r4,
  TDD-FPACH-CCode16-r4,
  TDD-UL-Interference,
  TDD-PICH-CCode,
  TDD-PRACH-CCode8,
  TDD-PRACH-CCode16,
  TDD-PRACH-CCode-LCR-r4,
  TDD-PRACH-CCodeList,
  TFC-ControlDuration,
  TFCI-Coding,
  TGCFN,
  TGD,
  TGL,
  TGMP,
  TGP-Sequence,
  TGPS-Reconfiguration-CFN,
  TGP-SequenceList,
  TGP-SequenceShort,
  TGPL,
  TGPRC,
  TGPS-ConfigurationParams,
  TGPSI,
  TGSN,
  TimeInfo,
  TimeslotList,
  TimeslotList-r4,
  TimeslotNumber,
  TimeslotNumber-LCR-r4,
  TimeslotNumber-PRACH-LCR-r4,
  TimeslotSync2,
  TimingOffset,
  TimingMaintainedSynchInd,
  TPC-CombinationIndex,
  TPC-StepSizeFDD,
  TPC-StepSizeTDD,
  TreconfirmAbort,
  TX-DiversityMode,
  UARFCN,
  UCSM-Info,
  UL-16QAM-Settings,
  UL-CCTrCH,
  UL-CCTrCH-r4,
  UL-CCTrCHList,
  UL-CCTrCHList-r4,
  UL-CCTrCHListToRemove,
  UL-CCTrChTPCList,
  UL-ChannelRequirement,
  UL-ChannelRequirement-r4,
  UL-ChannelRequirement-r5,
  UL-ChannelRequirementWithCPCH-SetID,
  UL-ChannelRequirementWithCPCH-SetID-r4,
  UL-ChannelRequirementWithCPCH-SetID-r5,
  UL-CompressedModeMethod,
  UL-DL-Mode,
  UL-DPCCH-SlotFormat,
  UL-DPCH-Info,
  UL-DPCH-Info-r4,
  UL-DPCH-Info-r5,
  UL-DPCH-Info-r6,
  UL-DPCH-Info-r7,
  UL-DPCH-Info-r11,
  UL-DPCH-InfoPostFDD,
  UL-DPCH-InfoPostTDD,
  UL-DPCH-InfoPostTDD-LCR-r4,
  UL-DPCH-InfoPredef,
  UL-DPCH-PowerControlInfo,
  UL-DPCH-PowerControlInfo-r4,
  UL-DPCH-PowerControlInfo-r5,
  UL-DPCH-PowerControlInfo-r6,
  UL-DPCH-PowerControlInfoPostFDD,
  UL-DPCH-PowerControlInfoPostTDD,
  UL-DPCH-PowerControlInfoPostTDD-LCR-r4,
  UL-DPCH-PowerControlInfoPredef,
  UL-EDCH-Information-r6,
  UL-Interference,
  UL-ScramblingCode,
  UL-SynchronisationParameters-r4,
  UL-TargetSIR,
  UL-TimingAdvance,
  UL-TimingAdvanceControl,
  UL-TimingAdvanceControl-r4,
  UL-TimingAdvanceControl-LCR-r4,
  UL-TS-ChannelisationCode,
  UL-TS-ChannelisationCodeList,
  UplinkAdditionalTimeslots,
  UplinkAdditionalTimeslots-LCR-r4,
  Uplink-DPCCH-Slot-Format-Information,
  UplinkTimeslotsCodes,
  UplinkTimeslotsCodes-LCR-r4,
  Wi-LCR,
  AcquisitionSatInfo,
  AcquisitionSatInfoList,
  AdditionalMeasurementID-List,
  AlmanacSatInfo,
  AlmanacSatInfoList,
  AverageRLC-BufferPayload,
  AzimuthAndElevation,
  BadSatList,
  Frequency-Band,
  BCCH-ARFCN,
  BLER-MeasurementResults,
  BLER-MeasurementResultsList,
  BLER-TransChIdList,
  BSIC-VerificationRequired,
  BSICReported,
  BurstModeParameters,
  CellDCH-ReportCriteria,
  CellDCH-ReportCriteria-LCR-r4,
  CellIndividualOffset,
  CellInfo,
  CellInfo-r4,
  CellInfoSI-RSCP,
  CellInfoSI-RSCP-LCR-r4,
  CellInfoSI-ECN0,
  CellInfoSI-ECN0-LCR-r4,
  CellInfoSI-HCS-RSCP,
  CellInfoSI-HCS-RSCP-LCR-r4,
  CellInfoSI-HCS-ECN0,
  CellInfoSI-HCS-ECN0-LCR-r4,
  CellMeasuredResults,
  CellMeasurementEventResults,
  CellMeasurementEventResults-LCR-r4,
  CellReportingQuantities,
  CellSelectReselectInfoSIB-11-12,
  CellSelectReselectInfoSIB-11-12-RSCP,
  CellSelectReselectInfoSIB-11-12-ECN0,
  CellSelectReselectInfoSIB-11-12-HCS-RSCP,
  CellSelectReselectInfoSIB-11-12-HCS-ECN0,
  CellSelectReselectInfo-v590ext,
  CellSelectReselectInfoPCHFACH-v5b0ext,
  CellSelectReselectInfoTreselectionScaling-v5c0ext,
  CellsForInterFreqMeasList,
  CellsForInterRATMeasList,
  CellsForIntraFreqMeasList,
  CellSynchronisationInfo,
  CellToReport,
  CellToReportList,
  CodePhaseSearchWindow,
  CountC-SFN-Frame-difference,
  CPICH-Ec-N0,
  CPICH-RSCP,
  DeltaPRC,
  DeltaQrxlevmin,
  DeltaRSCP,
  DeltaRSCPPerCell,
  DeltaRRC,
  DGPS-CorrectionSatInfo,
  DGPS-CorrectionSatInfoList,
  DiffCorrectionStatus,
  DL-TransportChannelBLER,
  DopplerUncertainty,
  DRX-Info,
  EllipsoidPoint,
  EllipsoidPointAltitude,
  EllipsoidPointAltitudeEllipsoide,
  EllipsoidPointUncertCircle,
  EllipsoidPointUncertEllipse,
  EnvironmentCharacterisation,
  Event1a,
  Event1a-r4,
  Event1a-LCR-r4,
  Event1b,
  Event1b-r4,
  Event1b-LCR-r4,
  Event1c,
  Event1d,
  Event1e,
  Event1e-r6,
  Event1f,
  Event1f-r6,
  Event1j-r6,
  Event2a,
  Event2a-r6,
  Event2b,
  Event2b-r6,
  Event2c,
  Event2c-r6,
  Event2d,
  Event2d-r6,
  Event2e,
  Event2e-r6,
  Event2f,
  Event2f-r6,
  Event3a,
  Event3b,
  Event3c,
  Event3d,
  EventIDInterFreq,
  EventIDInterRAT,
  EventIDIntraFreq,
  EventResults,
  ExtraDopplerInfo,
  FACH-MeasurementOccasionInfo,
  FACH-MeasurementOccasionInfo-LCR-r4-ext,
  FilterCoefficient,
  FineSFN-SFN,
  ForbiddenAffectCell,
  ForbiddenAffectCell-r4,
  ForbiddenAffectCell-LCR-r4,
  ForbiddenAffectCellList,
  ForbiddenAffectCellList-r4,
  ForbiddenAffectCellList-LCR-r4,
  FreqQualityEstimateQuantity-FDD,
  FreqQualityEstimateQuantity-TDD,
  GPS-MeasurementParam,
  GPS-MeasurementParamList,
  GSM-CarrierRSSI,
  GSM-MeasuredResults,
  GSM-MeasuredResultsList,
  GPS-TOW-1msec,
  GPS-TOW-Assist,
  GPS-TOW-AssistList,
  HCS-CellReselectInformation-RSCP,
  HCS-CellReselectInformation-ECN0,
  HCS-NeighbouringCellInformation-RSCP,
  HCS-NeighbouringCellInformation-ECN0,
  HCS-PRIO,
  HCS-ServingCellInformation,
  Hysteresis,
  HysteresisInterFreq,
  InterFreqCell,
  InterFreqCell-LCR-r4,
  InterFreqCellID,
  InterFreqCellInfoList,
  InterFreqCellInfoList-r4,
  InterFreqCellInfoSI-List-RSCP,
  InterFreqCellInfoSI-List-ECN0,
  InterFreqCellInfoSI-List-HCS-RSCP,
  InterFreqCellInfoSI-List-HCS-ECN0,
  InterFreqCellInfoSI-List-RSCP-LCR,
  InterFreqCellInfoSI-List-ECN0-LCR,
  InterFreqCellInfoSI-List-HCS-RSCP-LCR,
  InterFreqCellInfoSI-List-HCS-ECN0-LCR,
  InterFreqCellList,
  InterFreqCellList-LCR-r4-ext,
  InterFreqCellMeasuredResultsList,
  InterFreqEvent,
  InterFreqEvent-r6,
  InterFreqEventList,
  InterFreqEventList-r6,
  InterFrequencyMeasuredResultsList-v590ext,
  Inter-FreqEventCriteria-v590ext,
  Inter-FreqEventCriteriaList-v590ext,
  Intra-FreqEventCriteriaList-v590ext,
  IntraFrequencyMeasuredResultsList-v590ext,
  IntraFreqReportingCriteria-1b-r5,
  PeriodicReportingInfo-1b,
  InterFreqEventResults,
  InterFreqEventResults-LCR-r4-ext,
  InterFreqMeasQuantity,
  InterFreqMeasuredResults,
  InterFreqMeasuredResultsList,
  InterFreqMeasurementSysInfo-RSCP,
  InterFreqMeasurementSysInfo-ECN0,
  InterFreqMeasurementSysInfo-HCS-RSCP,
  InterFreqMeasurementSysInfo-HCS-ECN0,
  InterFreqMeasurementSysInfo-RSCP-LCR-r4,
  InterFreqMeasurementSysInfo-ECN0-LCR-r4,
  InterFreqMeasurementSysInfo-HCS-RSCP-LCR-r4,
  InterFreqMeasurementSysInfo-HCS-ECN0-LCR-r4,
  InterFreqRACHRepCellsList,
  Dummy-InterFreqRACHReportingInfo,
  InterFreqRACHReportingInfo,
  InterFreqReportCriteria,
  InterFreqReportCriteria-r4,
  InterFreqReportCriteria-r6,
  InterFreqReportingCriteria,
  InterFreqReportingCriteria-r6,
  InterFreqReportingQuantity,
  InterFreqRepQuantityRACH-FDD,
  InterFreqRepQuantityRACH-TDD,
  InterFreqRepQuantityRACH-TDDList,
  InterFrequencyMeasurement,
  InterFrequencyMeasurement-r4,
  InterFrequencyMeasurement-r6,
  InterRAT-TargetCellDescription,
  InterRATCellID,
  InterRATCellInfoIndication,
  InterRATCellInfoList,
  InterRATCellInfoList-B,
  InterRATCellInfoList-r4,
  InterRATCellInfoList-r6,
  InterRATCellIndividualOffset,
  InterRATEvent,
  InterRATEventList,
  InterRATEventResults,
  InterRATInfo,
  InterRATInfo-r6,
  InterRATMeasQuantity,
  InterRATMeasuredResults,
  InterRATMeasuredResultsList,
  InterRATMeasurement,
  InterRATMeasurement-r4,
  InterRATMeasurement-r6,
  InterRATMeasurementSysInfo,
  InterRATMeasurementSysInfo-B,
  InterRATReportCriteria,
  InterRATReportingCriteria,
  InterRATReportingQuantity,
  IntraFreqCellID,
  IntraFreqCellInfoList,
  IntraFreqCellInfoList-r4,
  IntraFreqCellInfoSI-List-RSCP,
  IntraFreqCellInfoSI-List-ECN0,
  IntraFreqCellInfoSI-List-HCS-RSCP,
  IntraFreqCellInfoSI-List-HCS-ECN0,
  IntraFreqCellInfoSI-List-RSCP-LCR-r4,
  IntraFreqCellInfoSI-List-ECN0-LCR-r4,
  IntraFreqCellInfoSI-List-HCS-RSCP-LCR-r4,
  IntraFreqCellInfoSI-List-HCS-ECN0-LCR-r4,
  IntraFreqEvent,
  IntraFreqEvent-r4,
  IntraFreqEvent-LCR-r4,
  IntraFreqEvent-r6,
  IntraFreqEvent-1d-r5,
  IntraFreqEventCriteria,
  IntraFreqEventCriteria-r4,
  IntraFreqEventCriteria-LCR-r4,
  IntraFreqEventCriteria-r6,
  IntraFreqEventCriteriaList,
  IntraFreqEventCriteriaList-r4,
  IntraFreqEventCriteriaList-LCR-r4,
  IntraFreqEventCriteriaList-r6,
  IntraFreqEventResults,
  IntraFreqMeasQuantity,
  IntraFreqMeasQuantity-FDD,
  IntraFreqMeasQuantity-TDD,
  IntraFreqMeasQuantity-TDDList,
  IntraFreqMeasuredResultsList,
  IntraFreqMeasurementSysInfo-RSCP,
  IntraFreqMeasurementSysInfo-ECN0,
  IntraFreqMeasurementSysInfo-HCS-RSCP,
  IntraFreqMeasurementSysInfo-HCS-ECN0,
  IntraFreqMeasurementSysInfo-RSCP-LCR-r4,
  IntraFreqMeasurementSysInfo-ECN0-LCR-r4,
  IntraFreqMeasurementSysInfo-HCS-RSCP-LCR-r4,
  IntraFreqMeasurementSysInfo-HCS-ECN0-LCR-r4,
  IntraFreqReportCriteria,
  IntraFreqReportCriteria-r4,
  IntraFreqReportCriteria-r6,
  IntraFreqReportingCriteria,
  IntraFreqReportingCriteria-r4,
  IntraFreqReportingCriteria-LCR-r4,
  IntraFreqReportingCriteria-r6,
  IntraFreqReportingQuantity,
  IntraFreqReportingQuantityForRACH,
  IntraFreqRepQuantityRACH-FDD,
  IntraFreqRepQuantityRACH-TDD,
  IntraFreqRepQuantityRACH-TDDList,
  IntraFrequencyMeasurement,
  IntraFrequencyMeasurement-r4,
  IntraFrequencyMeasurement-r6,
  IODE,
  IP-Length,
  IP-PCCPCH-r4,
  IP-Spacing,
  IP-Spacing-TDD,
  IS-2000SpecificMeasInfo,
  MaxNumberOfReportingCellsType1,
  MaxNumberOfReportingCellsType2,
  MaxNumberOfReportingCellsType3,
  MaxReportedCellsOnRACH,
  MaxReportedCellsOnRACHinterFreq,
  MeasuredResults,
  MeasuredResults-v390ext,
  MeasuredResults-v590ext,
  MeasuredResults-LCR-r4,
  MeasuredResultsList,
  MeasuredResultsList-LCR-r4-ext,
  MeasuredResultsOnRACH,
  MeasuredResultsOnRACHinterFreq,
  MeasurementCommand,
  MeasurementCommand-r4,
  MeasurementCommand-r6,
  MeasurementControlSysInfo,
  MeasurementControlSysInfoExtension,
  MeasurementControlSysInfoExtensionAddon-r5,
  MeasurementControlSysInfoExtension-LCR-r4,
  MeasurementControlSysInfo-LCR-r4-ext,
  MeasurementIdentity,
  MeasurementQuantityGSM,
  MeasurementReportingMode,
  MeasurementType,
  MeasurementType-r4,
  MeasurementType-r6,
  MeasurementValidity,
  MonitoredCellRACH-List,
  MonitoredCellRACH-Result,
  MultipathIndicator,
  N-CR-T-CRMaxHyst,
  NavigationModelSatInfo,
  NavigationModelSatInfoList,
  EphemerisParameter,
  NC-Mode,
  Neighbour,
  Neighbour-v390ext,
  NeighbourList,
  NeighbourList-v390ext,
  NeighbourQuality,
  NewInterFreqCell,
  NewInterFreqCell-r4,
  NewInterFreqCellList,
  NewInterFreqCellList-r4,
  NewInterFreqCellSI-RSCP,
  NewInterFreqCellSI-ECN0,
  NewInterFreqCellSI-HCS-RSCP,
  NewInterFreqCellSI-HCS-ECN0,
  NewInterFreqCellSI-RSCP-LCR-r4,
  NewInterFreqCellSI-ECN0-LCR-r4,
  NewInterFreqCellSI-HCS-RSCP-LCR-r4,
  NewInterFreqCellSI-HCS-ECN0-LCR-r4,
  NewInterFreqCellSI-List-ECN0,
  NewInterFreqCellSI-List-HCS-RSCP,
  NewInterFreqCellSI-List-HCS-ECN0,
  NewInterFreqCellSI-List-RSCP,
  NewInterFreqCellSI-List-ECN0-LCR-r4,
  NewInterFreqCellSI-List-HCS-RSCP-LCR-r4,
  NewInterFreqCellSI-List-HCS-ECN0-LCR-r4,
  NewInterFreqCellSI-List-RSCP-LCR-r4,
  NewInterRATCell,
  NewInterRATCell-B,
  NewInterRATCellList,
  NewInterRATCellList-B,
  NewIntraFreqCell,
  NewIntraFreqCell-r4,
  NewIntraFreqCellList,
  NewIntraFreqCellList-r4,
  NewIntraFreqCellSI-RSCP,
  NewIntraFreqCellSI-ECN0,
  NewIntraFreqCellSI-HCS-RSCP,
  NewIntraFreqCellSI-HCS-ECN0,
  NewIntraFreqCellSI-RSCP-LCR-r4,
  NewIntraFreqCellSI-ECN0-LCR-r4,
  NewIntraFreqCellSI-HCS-RSCP-LCR-r4,
  NewIntraFreqCellSI-HCS-ECN0-LCR-r4,
  NewIntraFreqCellSI-List-RSCP,
  NewIntraFreqCellSI-List-ECN0,
  NewIntraFreqCellSI-List-HCS-RSCP,
  NewIntraFreqCellSI-List-HCS-ECN0,
  NewIntraFreqCellSI-List-RSCP-LCR-r4,
  NewIntraFreqCellSI-List-ECN0-LCR-r4,
  NewIntraFreqCellSI-List-HCS-RSCP-LCR-r4,
  NewIntraFreqCellSI-List-HCS-ECN0-LCR-r4,
  NonUsedFreqParameter,
  NonUsedFreqParameter-r6,
  NonUsedFreqParameterList,
  NonUsedFreqParameterList-r6,
  NonUsedFreqWList-r6,
  ObservedTimeDifferenceToGSM,
  OTDOA-SearchWindowSize,
  Pathloss,
  PenaltyTime-RSCP,
  PenaltyTime-ECN0,
  PendingTimeAfterTrigger,
  PeriodicalOrEventTrigger,
  PeriodicalReportingCriteria,
  PeriodicalWithReportingCellStatus,
  PLMNIdentitiesOfNeighbourCells,
  PLMNsOfInterFreqCellsList,
  PLMNsOfIntraFreqCellsList,
  PLMNsOfInterRATCellsList,
  PositionEstimate,
  PositioningMethod,
  PRC,
  PrimaryCCPCH-RSCP,
  Q-HCS,
  Q-OffsetS-N,
  Q-QualMin,
  Q-RxlevMin,
  QualityEventResults,
  QualityMeasuredResults,
  QualityMeasurement,
  QualityReportCriteria,
  QualityReportingCriteria,
  QualityReportingCriteriaSingle,
  QualityReportingQuantity,
  RAT-Type,
  ReferenceCellPosition,
  ReferenceLocation,
  ReferenceTimeDifferenceToCell,
  RemovedInterFreqCellList,
  RemovedInterRATCellList,
  RemovedIntraFreqCellList,
  ReplacementActivationThreshold,
  ReportDeactivationThreshold,
  ReportingAmount,
  ReportingCellStatus,
  ReportingCellStatusOpt,
  ReportingInfoForCellDCH,
  ReportingInfoForCellDCH-LCR-r4,
  ReportingInterval,
  ReportingIntervalLong,
  ReportingRange,
  RL-AdditionInfoList,
  RL-InformationLists,
  RLC-BuffersPayload,
  RRC,
  SatData,
  SatDataList,
  SatelliteStatus,
  SatID,
  SFN-Offset-Validity,
  SFN-SFN-Drift,
  SFN-SFN-ObsTimeDifference,
  SFN-SFN-ObsTimeDifference1,
  SFN-SFN-ObsTimeDifference2,
  SFN-SFN-OTD-Type,
  SFN-SFN-RelTimeDifference1,
  SFN-TOW-Uncertainty,
  SIR,
  SIR-MeasurementList,
  SIR-MeasurementResults,
  SIR-TFCS,
  SIR-TFCS-List,
  SIR-TimeslotList,
  SubFrame1Reserved,
  T-ADVinfo,
  T-CRMax,
  T-CRMaxHyst,
  TemporaryOffset1,
  TemporaryOffset2,
  TemporaryOffsetList,
  Threshold,
  Threshold-r6,
  ThreholdNonUsedFrequency-deltaList,
  ThresholdPositionChange,
  ThresholdSFN-GPS-TOW,
  ThresholdSFN-SFN-Change,
  ThresholdUsedFrequency,
  ThresholdUsedFrequency-r6,
  TimeInterval,
  TimeslotInfo,
  TimeslotInfo-LCR-r4,
  TimeslotInfoList,
  TimeslotInfoList-LCR-r4,
  TimeslotInfoList-r4,
  TimeslotISCP,
  TimeslotISCP-List,
  TimeslotListWithISCP,
  TimeslotWithISCP,
  TimeToTrigger,
  TrafficVolumeEventParam,
  TrafficVolumeEventResults,
  TrafficVolumeEventType,
  TrafficVolumeMeasQuantity,
  TrafficVolumeMeasSysInfo,
  TrafficVolumeMeasuredResults,
  TrafficVolumeMeasuredResultsList,
  TrafficVolumeMeasurement,
  TrafficVolumeMeasurementObjectList,
  TrafficVolumeReportCriteria,
  TrafficVolumeReportCriteriaSysInfo,
  TrafficVolumeReportingCriteria,
  TrafficVolumeReportingQuantity,
  TrafficVolumeThreshold,
  TransChCriteria,
  TransChCriteriaList,
  TransferMode,
  TransmittedPowerThreshold,
  TriggeringCondition1,
  TriggeringCondition2,
  TX-InterruptionAfterTrigger,
  UDRE,
  UE-6AB-Event,
  UE-6FG-Event,
  UE-AutonomousUpdateMode,
  UE-InternalEventParam,
  UE-InternalEventParamList,
  UE-InternalEventResults,
  UE-InternalMeasQuantity,
  UE-InternalMeasuredResults,
  UE-InternalMeasuredResults-LCR-r4,
  UE-InternalMeasurement,
  UE-InternalMeasurement-r4,
  UE-InternalMeasurementSysInfo,
  UE-InternalReportCriteria,
  UE-InternalReportingCriteria,
  UE-InternalReportingQuantity,
  UE-InternalReportingQuantity-r4,
  UE-MeasurementQuantity,
  UE-RX-TX-ReportEntry,
  UE-RX-TX-ReportEntryList,
  UE-RX-TX-TimeDifferenceType1,
  UE-RX-TX-TimeDifferenceType2,
  UE-RX-TX-TimeDifferenceType2Info,
  UE-RX-TX-TimeDifferenceThreshold,
  UE-TransmittedPower,
  UE-TransmittedPowerTDD-List,
  UL-TrCH-Identity,
  UE-Positioning-Accuracy,
  UE-Positioning-CipherParameters,
  UE-Positioning-Error,
  UE-Positioning-ErrorCause,
  UE-Positioning-EventParam,
  UE-Positioning-EventParamList,
  UE-Positioning-EventSpecificInfo,
  UE-Positioning-GPS-AcquisitionAssistance,
  UE-Positioning-GPS-AdditionalAssistanceDataRequest,
  UE-Positioning-GPS-Almanac,
  UE-Positioning-GPS-AssistanceData,
  UE-Positioning-GPS-DGPS-Corrections,
  UE-Positioning-GPS-IonosphericModel,
  UE-Positioning-GPS-MeasurementResults,
  UE-Positioning-GPS-NavigationModel,
  UE-Positioning-GPS-NavModelAddDataReq,
  UE-Positioning-GPS-ReferenceCellInfo,
  UE-Positioning-GPS-ReferenceTime,
  UE-Positioning-GPS-UTC-Model,
  UE-Positioning-IPDL-Parameters,
  UE-Positioning-IPDL-Parameters-r4,
  UE-Positioning-IPDL-Parameters-TDD-r4-ext,
  UE-Positioning-MeasuredResults,
  UE-Positioning-MeasuredResults-v390ext,
  UE-Positioning-Measurement,
  UE-Positioning-Measurement-v390ext,
  UE-Positioning-Measurement-r4,
  UE-Positioning-MeasurementEventResults,
  UE-Positioning-MeasurementInterval,
  UE-Positioning-MethodType,
  UE-Positioning-OTDOA-AssistanceData,
  UE-Positioning-OTDOA-AssistanceData-r4,
  UE-Positioning-OTDOA-AssistanceData-r4ext,
  UE-Positioning-OTDOA-AssistanceData-UEB,
  UE-Positioning-IPDL-Parameters-TDDList-r4-ext,
  UE-Positioning-OTDOA-Measurement,
  UE-Positioning-OTDOA-Measurement-v390ext,
  UE-Positioning-OTDOA-NeighbourCellInfo,
  UE-Positioning-OTDOA-NeighbourCellInfo-r4,
  UE-Positioning-OTDOA-NeighbourCellInfo-UEB,
  UE-Positioning-OTDOA-NeighbourCellList,
  UE-Positioning-OTDOA-NeighbourCellList-r4,
  UE-Positioning-OTDOA-NeighbourCellList-UEB,
  UE-Positioning-OTDOA-Quality,
  UE-Positioning-OTDOA-ReferenceCellInfo,
  UE-Positioning-OTDOA-ReferenceCellInfo-r4,
  UE-Positioning-OTDOA-ReferenceCellInfo-UEB,
  UE-Positioning-PositionEstimateInfo,
  UE-Positioning-ReportCriteria,
  UE-Positioning-ReportingQuantity,
  UE-Positioning-ReportingQuantity-v390ext,
  UE-Positioning-ReportingQuantity-r4,
  UE-Positioning-ResponseTime,
  UTRA-CarrierRSSI,
  UTRAN-GPS-DriftRate,
  UTRAN-GPSReferenceTime,
  UTRAN-GPSReferenceTimeResult,
  VarianceOfRLC-BufferPayload,
  W,
  BCC,
  BCCH-ModificationInfo,
  BCCH-ModificationTime,
  BSIC,
  CBS-DRX-Level1Information,
  CBS-DRX-Level1Information-extension-r6,
  CDMA2000-Message,
  CDMA2000-MessageList,
  CDMA2000-UMTS-Frequency-List,
  CellValueTag,
  ExpirationTimeFactor,
  ExtSIBTypeInfoSchedulingInfo-List,
  ExtSIBTypeInfoSchedulingInfo,
  FDD-UMTS-Frequency-List,
  FrequencyInfoCDMA2000,
  GERAN-SystemInfoBlock,
  GERAN-SystemInformation,
  GSM-BA-Range,
  GSM-BA-Range-List,
  GSM-Classmark2,
  GSM-Classmark3,
  GSM-MessageList,
  GSM-MS-RadioAccessCapability,
  GsmSecurityCapability,
  GSM-TargetCellInfoList,
  GSM-TargetCellInfo,
  IdentificationOfReceivedMessage,
  InterRAT-ChangeFailureCause,
  GERANIu-MessageList,
  GERANIu-RadioAccessCapability,
  InterRAT-UE-RadioAccessCapability,
  InterRAT-UE-RadioAccessCapabilityList,
  InterRAT-UE-RadioAccessCapability-v590ext,
  InterRAT-UE-RadioAccessCapability-v690ext,
  InterRAT-UE-SecurityCapability,
  InterRAT-UE-SecurityCapList,
  InterRAT-HO-FailureCause,
  MasterInformationBlock,
  MasterInformationBlock-v690ext,
  MasterInformationBlock-v6b0ext-IEs,
  MIB-ValueTag,
  NCC,
  PLMN-ValueTag,
  PredefinedConfigIdentityAndValueTag,
  ProtocolErrorInformation,
  ReceivedMessageType,
  Rplmn-Information,
  Rplmn-Information-r4,
  SchedulingInformation,
  SchedulingInformationSIB,
  SchedulingInformationSIBSb,
  SegCount,
  SegmentIndex,
  SFN-Prime,
  SIB-Data-fixed,
  SIB-Data-variable,
  SIBOccurIdentity,
  SIBOccurrenceIdentityAndValueTag,
  SIBOccurValueTag,
  SIB-ReferenceList,
  SIBSb-ReferenceList,
  SIB-ReferenceListFACH,
  SIB-Type,
  SIB-TypeAndTag,
  SIBSb-TypeAndTag,
  SIB-TypeExt,
  SibOFF,
  SibOFF-List,
  SPS-Information-TDD128-r8,
  SysInfoType1,
  SysInfoType1-v3a0ext-IEs,
  SysInfoType2,
  SysInfoType3,
  SysInfoType3-v4b0ext-IEs,
  SysInfoType3-v590ext,
  SysInfoType3-v5c0ext-IEs,
  SysInfoType3-v670ext,
  SysInfoType4,
  SysInfoType4-v4b0ext-IEs,
  SysInfoType4-v590ext,
  SysInfoType4-v5b0ext-IEs,
  SysInfoType4-v5c0ext-IEs,
  SysInfoType5,
  SysInfoType5-v4b0ext-IEs,
  SysInfoType5-v590ext-IEs,
  SysInfoType5-v650ext-IEs,
  SysInfoType5-v680ext-IEs,
  SysInfoType5-v690ext-IEs,
  SysInfoType5bis,
  SysInfoType6,
  SysInfoType6-v4b0ext-IEs,
  SysInfoType6-v590ext-IEs,
  SysInfoType6-v650ext-IEs,
  SysInfoType6-v690ext-IEs,
  SysInfoType7,
  SysInfoType8,
  SysInfoType9,
  SysInfoType10,
  SysInfoType11,
  SysInfoType11-v4b0ext-IEs,
  SysInfoType11-v590ext-IEs,
  SysInfoType11-v690ext-IEs,
  SysInfoType11-v6b0ext-IEs,
  SysInfoType11bis,
  SysInfoType12,
  SysInfoType12-v4b0ext-IEs,
  SysInfoType12-v590ext-IEs,
  SysInfoType12-v690ext-IEs,
  SysInfoType12-v6b0ext-IEs,
  SysInfoType13,
  SysInfoType13-v3a0ext-IEs,
  SysInfoType13-v4b0ext-IEs,
  SysInfoType13-1,
  SysInfoType13-2,
  SysInfoType13-3,
  SysInfoType13-4,
  SysInfoType14,
  SysInfoType15,
  SysInfoType15-v4b0ext-IEs,
  SysInfoType15-1,
  SysInfoType15-2,
  SysInfoType15-3,
  SysInfoType15-4,
  SysInfoType15-4-v3a0ext,
  SysInfoType15-4-v4b0ext,
  SysInfoType15-5,
  SysInfoType15-5-v3a0ext,
  SysInfoType16,
  SysInfoType17,
  SysInfoType17-v4b0ext-IEs,
  SysInfoType17-v590ext-IEs,
  SysInfoType18,
  SysInfoType18-v6b0ext,
  SysInfoType19,
  SysInfoTypeSB1,
  SysInfoTypeSB1-v6b0ext,
  SysInfoTypeSB2,
  SysInfoTypeSB2-v6b0ext,
  TDD-UMTS-Frequency-List,
  ValueTagInfo,
  ANSI-41-GlobalServiceRedirectInfo,
  ANSI-41-PrivateNeighbourListInfo,
  ANSI-41-RAND-Information,
  ANSI-41-UserZoneID-Information,
  ANSI-41-NAS-Parameter,
  Min-P-REV,
  NAS-SystemInformationANSI-41,
  NID,
  P-REV,
  SID,
  MBMS-AccessProbabilityFactor,
  MBMS-CellGroupIdentity-r6,
  MBMS-CommonCCTrChIdentity,
  MBMS-CommonPhyChIdentity,
  MBMS-CommonRBIdentity,
  MBMS-CommonRBInformation-r6,
  MBMS-CommonRBInformationList-r6,
  MBMS-CommonTrChIdentity,
  MBMS-ConnectedModeCountingScope,
  MBMS-CurrentCell-SCCPCH-r6,
  MBMS-CurrentCell-SCCPCHList-r6,
  MBMS-FACHCarryingMTCH-List,
  MBMS-JoinedInformation-r6,
  MBMS-L1CombiningSchedule-32,
  MBMS-L1CombiningSchedule-64,
  MBMS-L1CombiningSchedule-128,
  MBMS-L1CombiningSchedule-256,
  MBMS-L1CombiningSchedule-512,
  MBMS-L1CombiningSchedule-1024,
  MBMS-L1CombiningSchedule,
  MBMS-L1CombiningTransmTimeDiff,
  MBMS-L23Configuration,
  MBMS-LogicalChIdentity,
  MBMS-MCCH-ConfigurationInfo-r6,
  MBMS-MICHConfigurationInfo-r6,
  MBMS-MICHNotificationIndLength,
  MBMS-MICHPowerOffset,
  MBMS-ModifedService-r6,
  MBMS-ModifedServiceList-r6,
  MBMS-MSCH-ConfigurationInfo-r6,
  MBMS-MSCHSchedulingInfo,
  MBMS-NeighbouringCellSCCPCH-r6,
  MBMS-NeighbouringCellSCCPCHList-r6,
  MBMS-NI-CountPerFrame,
  MBMS-NumberOfNeighbourCells-r6,
  MBMS-PFLIndex,
  MBMS-PFLInfo,
  MBMS-PhyChInformation-r6,
  MBMS-PhyChInformationList-r6,
  MBMS-PL-ServiceRestrictInfo-r6,
  MBMS-PreferredFrequencyList-r6,
  MBMS-PTMActivationTime-r6,
  MBMS-PTM-RBInformation-C,
  MBMS-PTM-RBInformation-CList,
  MBMS-PTM-RBInformation-N,
  MBMS-PTM-RBInformation-NList,
  MBMS-Qoffset,
  MBMS-RequiredUEAction-Mod,
  MBMS-RequiredUEAction-UMod,
  MBMS-SCCPCHIdentity,
  MBMS-SCCPCHPwrOffsetDiff,
  MBMS-SelectedServiceInfo,
  MBMS-SelectedServicesListFull,
  MBMS-SelectedServicesListShort,
  MBMS-SelectedServicesShort,
  MBMS-ServiceAccessInfo-r6,
  MBMS-ServiceAccessInfoList-r6,
  MBMS-ServiceIdentity-r6,
  MBMS-ServiceSchedulingInfo-r6,
  MBMS-ServiceSchedulingInfoList-r6,
  MBMS-ServiceTransmInfo,
  MBMS-ServiceTransmInfoList,
  MBMS-SessionIdentity,
  MBMS-ShortTransmissionID,
  MBMS-SIBType5-SCCPCH-r6,
  MBMS-SIBType5-SCCPCHList-r6,
  MBMS-SoftComb-TimingOffset,
  MBMS-TCTF-Presence,
  MBMS-TimersAndCounters-r6,
  MBMS-TransmissionIdentity,
  MBMS-TranspChInfoForCCTrCh-r6,
  MBMS-TranspChInfoForEachCCTrCh-r6,
  MBMS-TranspChInfoForEachTrCh-r6,
  MBMS-TranspChInfoForTrCh-r6,
  MBMS-TrCHInformation-Curr,
  MBMS-TrCHInformation-CurrList,
  MBMS-TrCHInformation-Neighb,
  MBMS-TrCHInformation-NeighbList,
  MBMS-TrCHInformation-SIB5,
  MBMS-TrCHInformation-SIB5List,
  MBMS-UnmodifiedService-r6,
  MBMS-UnmodifiedServiceList-r6,
  MIMO-Parameters-r7,
  MIMO-Parameters-r8,
  MIMO-Parameters-r9,
  hiPDSCHidentities,
  hiPUSCHidentities,
  hiRM,
  maxAC,
  maxAdditionalMeas,
  maxASC,
  maxASCmap,
  maxASCpersist,
  maxCCTrCH,
  maxCellMeas,
  maxCellMeas-1,
  maxCNdomains,
  maxCPCHsets,
  maxDPCH-DLchan,
  maxDPDCH-UL,
  maxDRACclasses,
  maxE-DCHMACdFlow,
  maxE-DCHMACdFlow-1,
  maxEDCHRL,
  maxFACHPCH,
  maxFreq,
  maxFreqBandsFDD,
  maxFreqBandsFDD-ext,
  maxFreqBandsTDD,
  maxFreqBandsGSM,
  maxGERAN-SI,
  maxGSMTargetCells,
  maxHProcesses,
  maxHSDSCHTBIndex,
  maxHSDSCHTBIndex-tdd384,
  maxHSSCCHs,
  maxInterSysMessages,
  maxLoCHperRLC,
  maxMAC-d-PDUsizes,
  maxMBMS-CommonCCTrCh,
  maxMBMS-CommonPhyCh,
  maxMBMS-CommonRB,
  maxMBMS-CommonTrCh,
  maxMBMS-Freq,
  maxMBMS-L1CP,
  maxMBMSservCount,
  maxMBMSservModif,
  maxMBMSservSched,
  maxMBMSservSelect,
  maxMBMSservUnmodif,
  maxMBMSTransmis,
  maxMeasEvent,
  maxMeasIntervals,
  maxMeasParEvent,
  maxNumCDMA2000Freqs,
  maxNumGSMFreqRanges,
  maxNumE-HICH,
  maxNumFDDFreqs,
  maxNumTDDFreqs,
  maxNoOfMeas,
  maxOtherRAT,
  maxOtherRAT-16,
  maxPage1,
  maxPCPCH-APsig,
  maxPCPCH-APsubCh,
  maxPCPCH-CDsig,
  maxPCPCH-CDsubCh,
  maxPCPCH-SF,
  maxPCPCHs,
  maxPDCPAlgoType,
  maxPDSCH,
  maxPDSCH-TFCIgroups,
  maxPRACH,
  maxPRACH-FPACH,
  maxPredefConfig,
  maxPUSCH,
  maxQueueIDs,
  maxRABsetup,
  maxRAT,
  maxRB,
  maxRBallRABs,
  maxRBMuxOptions,
  maxRBperRAB,
  maxRBperTrCh,
  maxReportedGSMCells,
  maxRL,
  maxRL-1,
  maxRLCPDUsizePerLogChan,
  maxRFC3095-CID,
  maxROHC-PacketSizes-r4,
  maxROHC-Profile-r4,
  maxSat,
  maxSCCPCH,
  maxSIB,
  maxSIB-FACH,
  maxSIBperMsg,
  maxSRBsetup,
  maxSystemCapability,
  maxTF,
  maxTF-CPCH,
  maxTFC,
  maxTFCsub,
  maxTFCI-2-Combs,
  maxTGPS,
  maxTrCH,
  maxTrCHpreconf,
  maxTS,
  maxTS-1,
  maxTS-2,
  maxTS-LCR,
  maxTS-LCR-1,
  maxURA,
  maxURNTI-Group,
  HS-DSCH-DrxCycleFach,
  HS-DSCH-DrxBurstFach,
  T-321,
  RLC-PDU-SizeConstraint,
  CS-HSPA-Information,
  CellDCHMeasOccasionInfo-TDD128-r9,
  HS-DSCH-DrxCellfach-info,  -- @sic R5-145647 feFACH: type to be imported not defined sic@
  HS-DSCH-DrxCellfach-SecondDrx-info,  -- @sic R5-150125 feFACH sic@
  TFCS-r12,
  DL-CommonInformation-r12,
  DL-DPCH-InfoPerRL-r12,
  DL-HSPDSCH-Information-r12,
  DRX-Info-r12,
  DCH-Enhancements-Info-FDD -- @sic R5-155059 DCH_Enh sic@
  FROM UTRAN-RRC-ASN1-Definitions
;

maxLogCHperTrCH        INTEGER ::= 15
    --   This constant is from MCI ASP proposal, but there is no value for it in the proposal. value 8 is for temporary use
maxdlTrCH        INTEGER ::= 16
maxulTrCH        INTEGER ::= 16
maxNumOfSecondFrequency     INTEGER ::= 12
maxPDSCHtimeslot	INTEGER ::= 5

--**************************************************************
--
-- AICHInfo
-- When e-AI-Info  is present: 
--  upon receipt of the access preamble signature corresponding to a PRACH message transmission i.e preambleSignature, the Acquisition Indicators is transmitted on AICH 
--  upon receipt of the access preamble signature corresponding to an E-DCH transmission  i.e. commonEDCH-PreambleSignature, the Extended Acquisition Indicators is transmitted on AICH. 
--**************************************************************

AICHInfo ::= SEQUENCE {
  aichinfo AICH-Info,
  dl-TxPower AICH-PowerOffset,
  e-AI-Info E-AI-InfoType  OPTIONAL    -- Rel-8 or later @sic R5-110104 sic@
}

---**************************************************************
--
-- E-AI-InfoType
--
--**************************************************************
E-AI-InfoType ::= SEQUENCE {
  defaultE-DCH-ResourceIndex   INTEGER (-1..31),
  totalNumberE-DCH          INTEGER (1..32)
}

--**************************************************************
--
-- DL-TxPower-PCCPCH
--TDD
--**************************************************************

DL-TxPower-PCCPCH ::= INTEGER (-60..-30 )

--**************************************************************
--
-- AmConfirmationRequest
--   If the noConfirmationRequested option is used, then an RLC-AM-DATA-CNF is not expected from the RLC AM entity.
--   If the confirmationRequested option is used, then the RLC AM entity is being requested to provide an RLC-DATA-CNF primitive containing the same mui value.
--
--**************************************************************

AmConfirmationRequest ::= CHOICE {
  noConfirmationRequest NULL,
  confirmationRequested Mui
}

--**************************************************************
--
-- COUNT-I-MSB
--   28 bits long
--
--**************************************************************

COUNT-I-MSB ::= INTEGER (0..268435455 )

--**************************************************************
--
-- CellToBeCreated
--
--**************************************************************

CellToBeCreated ::= ENUMERATED { cell-DCH (0), cell-FACH (10) }

--**************************************************************
--
-- CellTxPowerLevel
--   The defaultCellTxPowerLvl is a default setting and is used for the most signalling tests. The real total cell DL Tx power level equals to the sum of the DL Tx power of the individual physical channels configured.
--   The totalCellTxPowerLvl applies to e.g. the idle mode tests in a non-default multi-cell radio environment.
--
--**************************************************************

CellTxPowerLevel ::= CHOICE
{
  defaultCellTxPowerLvl NULL,
  totalCellTxPowerLvl DL-TxPower
}

--**************************************************************
--
-- CfnTgtSfnFrameOffset
--   1. The observedValue is provided if the UE reads SFN when measuring "Cell synchronisation information" and sends it to the SS in MEASUREMENT REPORT message. The OFF value in IE COUNT-C-SFN frame difference is applied to the observedValue.
--   2. If the synchronisation between the target cell and the reference cell is calculated the calculatedAbsoluteValue is applied. Depending upon how to interpret SfnOffset two valid calculations exist.
--   2.1 If SfnOffset is interpreted as the frames lagging behind:
--   calculated-sfnLagging = (((4096 * 38400) + SfnOffset- Ref * 38400 +TCell-Ref + DOFF*512 - (SfnOffset-Tgt * 38400 + TCell-Tgt)) mod (256 * 38400)) / 38400
--   2.2 If SfnOffset is interpreted as the frames in advance:
--   calculated-sfnInAdvance = (((4096 + SfnOffset-Tgt - SfnOffset- Ref) * 38400 +TCell-Ref + DOFF*512 - TCell-Tgt) mod (256 * 38400)) / 38400
--   The formula can be further simplified in the default condition if SfnOffset- Ref and TCell-Ref are equal to 0:
--   calculated-sfnLagging = (((4096 * 38400) + DOFF*512 - (SfnOffset-Tgt * 38400 + TCell-Tgt)) mod (256 * 38400)) / 38400
--   calculated-sfnInAdvance = ((DOFF*512 + SfnOffset-Tgt * 38400 - TCell-Tgt) Mod (256 * 38400)) / 38400
--   calculated-sfnInAdvance = (calculated-sfnLagging + 2* SfnOffset-Tgt) mod 256
--   calculated-sfnLagging = (calculated-sfnInAdvance + (4096 - SfnOffset-Tgt) * 2) mod 256
--   The TTCN provides calculated-sfnLagging.
--
--**************************************************************

CfnTgtSfnFrameOffset ::= SEQUENCE {
  referenceCellId INTEGER (0..63),
  cfnFrameOffset CHOICE {
    observed INTEGER (0..255),
    calculated INTEGER (0..255) }
}

--**************************************************************
--
-- CiphActivationInfo
--   DL or UL ciphering activation infoIf RB is omitted in rB-UL-CiphActivationTimeInfo the SS takes no action on this RB and the ciphering configuration keeps unchanged on this RB. CipheringModeCommand = dummy NULL means no ciphering.
--
--**************************************************************

CiphActivationInfo ::= CHOICE {
  cipheringModeInfo CipheringModeInfo,
  rb-UL-CipheringActivationTimeInfo RB-ActivationTimeInfoList,
  cipheringModeInfo-r7 CipheringModeInfo-r7
}

--**************************************************************
--
-- CmacConfigReq-FDD
--   To request to configure MAC
-- The IE associatedPhychConfigToFollow should be set to TRUE when there is a associated physical channel configuration to follow (e.g configuration of PICH or MICH).
-- The implementation of the IE "associatedPhychConfigToFollow" can be left to the SS either to wait for the associated physical channel before MAC is configured or to continue the configuration of MAC without waiting for the associated physical channel.
-- If Dual Cell is configured, IE servingAndSecondaryCellActivation is included.
-- Presence of tSN-FieldExtension indicates that the TSN field extension is used as defined in TS 25.321[17]; the absence indicates that 6 bits TSN is used. For 4C-HSDPA tSN-FieldExtension is set to TRUE.
--
--**************************************************************

CmacConfigReq-FDD ::= SEQUENCE {
  activationTime SS-ActivationTime,
  uE-Info UE-Info,
  trCHInfo TrCHInfo,
  trCH-LogCHMapping TrCH-LogCHMappingList1,
  associatedPhychConfigToFollow SEQUENCE (SIZE(1..4)) OF INTEGER OPTIONAL, 
  servingAndSecondaryCellActivation  ServingAndSecondaryCellActivation-Type  OPTIONAL,   -- for Dual Cell Rel-8 or later @sic R5-103863 sic@
  tSN-FieldExtension    BOOLEAN	DEFAULT FALSE,  -- Rel-9 or later
  relAspTypeExtension   CmacConfigReq-r10OrLaterExtensionType	OPTIONAL	-- Rel-10 or later @sic R5-130613 R5-134957 sic@
}

--**************************************************************
--
-- CmacConfigReq-TDD
--   To request to configure MAC
--
--**************************************************************

CmacConfigReq-TDD ::= SEQUENCE {
  activationTime SS-ActivationTime,
  uE-Info UE-Info,
  trCHInfo TrCHInfo-TDD,
  trCH-LogCHMapping TrCH-LogCHMappingList1-TDD, -- @sic R5-134957 R5w130320: TDD TTCN-2/3 differences sic@
  associatedPhychConfigToFollow SEQUENCE (SIZE(1..4)) OF INTEGER OPTIONAL,
  tSN-FieldExtension	BOOLEAN DEFAULT FALSE, -- Rel-9 or later @sic R5-134957 sic@
  relAspTypeExtension  SEQUENCE{} OPTIONAL -- Rel-10 or later @sic R5-134957 sic@
}

--**************************************************************
--
-- CmacPagingConfigReq
--
--**************************************************************

CmacPagingConfigReq ::= SEQUENCE {
  pI-BitMapInfo CHOICE {
    e18 BIT STRING (SIZE (18)),
    e36 BIT STRING (SIZE (36)),
    e72 BIT STRING (SIZE (72)),
    e144 BIT STRING (SIZE (144))},
  dRX-CycleLength INTEGER (3..9),
  iMSI IMSI-GSM-MAP,
  t-pich-T-sccpch BOOLEAN -- T-pich > T-sccpch then FALSE
}

--**************************************************************
--
-- CmacPagingConfigReq-TDD
--
--**************************************************************

CmacPagingConfigReq-TDD ::= SEQUENCE {
  pI-BitMapInfo CHOICE {
    two-PICH-frame   Two-PICH-pI-BitmapInfo,
    four-PICH-frame  Four-PICH-pI-BitmapInfo
    },
  dRX-CycleLength INTEGER (3..9),
  iMSI IMSI-GSM-MAP,
  t-pich-T-sccpch BOOLEAN -- T-pich > T-sccpch then FALSE
}

Two-PICH-pI-BitmapInfo ::= CHOICE {
    e44 BIT STRING (SIZE (44)),
    e88 BIT STRING (SIZE (88)),
    e176 BIT STRING (SIZE (176))
}

Four-PICH-pI-BitmapInfo ::= CHOICE {
    e88 BIT STRING (SIZE (88)),
    e176 BIT STRING (SIZE (176)),
    e352 BIT STRING (SIZE (352))
}
--**************************************************************
--
-- CmacSysinfoConfigReq
--   if bcch-ModificationTime = OMIT SS shall modify the Sysinfo immediately
--
--**************************************************************

CmacSysinfoConfigReq ::= SEQUENCE {
  sg-REP INTEGER (2..12),
  -- Repetition period is the sg-REP-th power of 2.
  sg-POS INTEGER (0..2047),
  -- The position of each segment is 2 * sg-POS.
  bcch-ModificationTime BCCH-ModificationTime OPTIONAL
}

--**************************************************************
--
-- CommonOrDedicatedTFS
--   Transport Format Set
--
--**************************************************************

CommonOrDedicatedTFS ::= SEQUENCE {
  tti CHOICE {
    tti10 CommonOrDedicatedTF-InfoList,
    tti20 CommonOrDedicatedTF-InfoList,
    tti40 CommonOrDedicatedTF-InfoList,
    tti80 CommonOrDedicatedTF-InfoList,
    dynamic CommonOrDedicatedTF-InfoList-DynamicTTI
  },
  semistaticTF-Information SemistaticTF-Information
}

--**************************************************************
--
-- CommonOrDedicatedTFS-TDD
--   Transport Format Set
--   CommonOrDedicatedTFS in TTCN-2
--
--**************************************************************

CommonOrDedicatedTFS-TDD ::= SEQUENCE {
  tfsMode CHOICE {
    dedicatedTransChTFS DedicatedTransChTFS,
    commonTransChTFS CommonTransChTFS,
    commonTransChTFS-LCR CommonTransChTFS-LCR
  }
}

--**************************************************************
--
-- CommonOrDedicatedTF-Info
--   Transport Format Set
--
--**************************************************************

CommonOrDedicatedTF-Info ::= SEQUENCE {
  tb-Size INTEGER (0..5035),
  numberOfTbSizeList SEQUENCE (SIZE (1..maxTF)) OF NumberOfTransportBlocks,
  logicalChannelList SS-LogicalChannelList
}

--**************************************************************
--
-- CommonOrDedicatedTF-InfoList
--   Transport Format Set
--
--**************************************************************

CommonOrDedicatedTF-InfoList ::= SEQUENCE (SIZE (1..maxTF)) OF CommonOrDedicatedTF-Info

--**************************************************************
--
-- CommonOrDedicatedTF-InfoList-DynamicTTI
--
--**************************************************************

CommonOrDedicatedTF-InfoList-DynamicTTI ::= SEQUENCE
{
  tb-Size INTEGER (0..5035),
  numberOfTbSizeList SEQUENCE (SIZE (1..maxTF)) OF NumberOfTransportBlocks,
  logicalChannelList SS-LogicalChannelList
}

--**************************************************************
--
-- CphyRlModifyReq-FDD
--
--**************************************************************

CphyRlModifyReq-FDD ::= SEQUENCE {
  activationTime SS-ActivationTime,
  physicalChannelInfo
  CHOICE {
    dpch-CompressedModeStatusInfo DPCH-CompressedModeStatusInfo,
    secondaryCCPCHInfo SecondaryCCPCHInfo-FDD,
    pRACHInfo PRACHInfo-FDD,
    dPCHInfo DPCHInfo-FDD,
    dPCHInfo-r5 DPCHInfo-r5OrLater-FDD, -- Rel-5 or later
    hS-PDSCHInfo HS-PDSCHInfo-r5OrLater-FDD, -- Rel-5 or later
    e-DPCHInfo SS-E-DPCH-Info-r6OrLater, -- Rel-6 or later
    e-AGCHInfo SS-E-AGCH-Info-FDD, -- Rel-6 or later
    e-HICHInfo SS-E-HICH-Info, -- Rel-6 or later
    e-RGCHInfo SS-E-RGCH-Info, -- Rel-6 or later
    mBMS-MICHInfo SS-MBMS-MICHConfigurationInfo-r6, -- Rel-6 or later @sic R5-112477 sic@
    aICHInfo   AICHInfo,
	relAspTypeExtension	 SEQUENCE{}	-- Rel-10 or later @sic R5-130613 R5-134957 sic@
  },
  trchConfigToFollow BOOLEAN DEFAULT TRUE,
  relAspTypeExtension CphyRlModifyReq-FDD-r10OrLaterExtensionType  OPTIONAL -- Rel-10 or later @sic R5-130613 R5-134957  R5-155059 sic@
}


--**************************************************************
--
-- CphyRlModifyReq-FDD-r10OrLaterExtensionType
-- Applicable Rel-12 or later 
-- Used only for DCH Enhancements
-- @sic R5-155059 sic@
--**************************************************************
CphyRlModifyReq-FDD-r10OrLaterExtensionType ::= CHOICE {
    rel12-AspExt SEQUENCE   {
        dch-EnhancementsInfo-FDD DCH-Enhancements-Info-FDD    OPTIONAL
    }
}

--**************************************************************
--
-- CphyRlModifyReq-TDD
--   To request to Modify the Radio Link
--
--**************************************************************

CphyRlModifyReq-TDD ::= SEQUENCE {
  activationTime     SS-ActivationTime,
  physicalChannelInfo CHOICE {    
    secondaryCCPCHInfo        SecondaryCCPCHInfo-TDD,
    pRACHInfo                 PRACHInfo-TDD,
    dPCHInfo                 DPCHInfo-TDD,
    dPCHInfo-r5             DPCHInfo-r5OrLater-TDD, -- Rel-5 or later
    hS-PDSCHInfo             HS-PDSCHInfo-r5OrLater-TDD, -- Rel-5 or later
    e-DCHInfo                 SS-E-DCH-Info-r7, 
    e-DCH-Non-ScheduledTransGrantInfo     SS-Non-ScheduledTransGrantInfoTDD,
    e-AGCHInfo                 SS-E-AGCH-Info-TDD, -- Rel-7 or later
    e-HICHInfo                 SS-E-HICH-Info-TDD, -- Rel-7 or later
    mBMS-MICHInfo             SS-MBMS-MICHConfigurationInfo-r6, -- Rel-6 or later @sic R5w140013 sic@
    relAspTypeExtension 	  SEQUENCE{} -- Rel-10 or later  @sic R5-134957 sic@
  },
  trchConfigToFollow     BOOLEAN DEFAULT TRUE,
  relAspTypeExtension 		SEQUENCE{} OPTIONAL -- Rel-10 or later  @sic R5-134957 sic@
}

--**************************************************************
--
-- CphyRlSetupReq-FDD
--   To request to setup the Radio Link
--
--**************************************************************

CphyRlSetupReq-FDD ::= SEQUENCE {
  physicalChannelInfo CHOICE {
    primaryCPICHInfo PrimaryCPICHInfo,
    secondaryCPICHInfo SecondaryCPICHInfo,
    primarySCHInfo PrimarySCHInfo,
    secondarySCHInfo SecondarySCHInfo,
    primaryCCPCHInfo PrimaryCCPCHInfo-FDD,
    secondaryCCPCHInfo SecondaryCCPCHInfo-FDD,
    pRACHInfo PRACHInfo-FDD,
    pICHInfo PICHInfo-FDD,
    aICHInfo AICHInfo,
    dPCHInfo DPCHInfo-FDD,
    pDSCHInfo PDSCHInfo-FDD,
    dPCHInfo-r5 DPCHInfo-r5OrLater-FDD, -- Rel-5 or later
    hS-PDSCHInfo HS-PDSCHInfo-r5OrLater-FDD, -- Rel-5 or later
    e-DPCHInfo SS-E-DPCH-Info-r6OrLater, -- Rel-6 or later
    e-AGCHInfo SS-E-AGCH-Info-FDD, -- Rel-6 or later
    e-HICHInfo SS-E-HICH-Info, -- Rel-6 or later
    e-RGCHInfo SS-E-RGCH-Info, -- Rel-6 or later
    mBMS-MICHInfo SS-MBMS-MICHConfigurationInfo-r6, -- Rel-6 or later @sic R5-112477 sic@
	relAspTypeExtension	SEQUENCE{}	-- Rel-10 or later @sic R5-130613 R5-134957 sic@
  },
  activationTime SS-ActivationTime, 
  trchConfigToFollow BOOLEAN DEFAULT TRUE,
  relAspTypeExtension  SEQUENCE{}  OPTIONAL	-- Rel-10 or later @sic R5-130613 R5-134957 sic@
}

--**************************************************************
--
-- CphyRlSetupReq-TDD
--   To request to setup the Radio Link
--
--**************************************************************

CphyRlSetupReq-TDD ::= SEQUENCE {
  physicalChannelInfo CHOICE {    
    primaryCCPCHInfo             PrimaryCCPCHInfo-TDD,
    secondaryCCPCHInfo             SecondaryCCPCHInfo-TDD,
    pRACHInfo                 PRACHInfo-TDD,
    pICHInfo                 PICHInfo-TDD,
    dPCHInfo                 DPCHInfo-TDD,
    pDSCHInfo                 PDSCHInfo-TDD,
    pUSCHInfo                 PUSCHInfo,
    dPCHInfo-r5             DPCHInfo-r5OrLater-TDD, -- Rel-5 or later
    hS-PDSCHInfo             HS-PDSCHInfo-r5OrLater-TDD, -- Rel-5 or later
    e-DCHInfo                 SS-E-DCH-Info-r7, 
    e-DCH-Non-ScheduledTransGrantInfo     SS-Non-ScheduledTransGrantInfoTDD,
    e-AGCHInfo                 SS-E-AGCH-Info-TDD, -- Rel-7 or later
    e-HICHInfo                 SS-E-HICH-Info-TDD, -- Rel-7 or later
    mBMS-MICHInfo             SS-MBMS-MICHConfigurationInfo-r6, -- Rel-6 or later @sic R5w140013 sic@
    relAspTypeExtension 	SEQUENCE{} -- Rel-10 or later  @sic R5-134957 sic@
  },
  activationTime     SS-ActivationTime OPTIONAL,
  trchConfigToFollow     BOOLEAN DEFAULT TRUE,
  relAspTypeExtension 	SEQUENCE{} OPTIONAL -- Rel-10 or later  @sic R5-134957 sic@
}

--**************************************************************
--
-- CphyTrchConfigReq
--   To request to configure the transport channel.
--   The same TFCS information should be provided to the PHY and MAC layers at all times. When a CPHY-TrCH-Config-REQ is used to configure the PHY layer, a corresponding CMAC-Config-REQ should be sent to the MAC layer to ensure that the configuration is consistent.
--   HS-DSCH MAC-d flows or E-DCH MAC-d flows shall be separately configured whilst the ulconnectedTrCHList, ulTFCS, dlconnectedTrCHList and dlTFCS are omitted.
--   For configuring MBMS if the default TFCS used in the RRC message the dLTFTS shall use the "complete" CHOICE in "ExplicitTFCS-Configuration " IE and the TFCS configuration shall be in line with clause 14.10.1.1/14.10.1.2 of TS 25.331.
--
--**************************************************************

CphyTrchConfigReq ::= SEQUENCE {
  activationTime SS-ActivationTime,
  ulconnectedTrCHList SEQUENCE (SIZE (0..maxTrCH)) OF SEQUENCE {
    trchid TransportChannelIdentity,
    ul-TransportChannelType SS-UL-TransportChannelType,
    transportChannelInfo CommonOrDedicatedTFS
  } OPTIONAL,
  ulTFCS TFCS OPTIONAL,
  dlconnectedTrCHList SEQUENCE (SIZE (0..maxTrCH)) OF SEQUENCE {
    trchid TransportChannelIdentity,
    dl-TransportChannelType SS-DL-TransportChannelType,
    transportChannelInfo CommonOrDedicatedTFS
  } OPTIONAL ,
  dlTFCS TFCS OPTIONAL,
  hsDSCHMacdFlows HS-DSCHMACdFlows OPTIONAL, -- Rel-5 or later
  e-DCHMacdFlows E-DCHMACdFlows OPTIONAL,    -- Rel-6 or later
  ehs-DSCH-Flows EHS-DSCH-Flows OPTIONAL,    -- Rel-7 or later
  ehs-DSCH-CommonFlows EHS-DSCH-CommonFlows OPTIONAL,    -- Rel-7 or later
  e-DCHMacd-CommonFlows CommonE-DCHMACdFlows OPTIONAL, -- Rel-8 or later
  ehs-DSCH-Flows-r9 EHS-DSCH-Flows-r9 OPTIONAL,    -- Rel-9 or later @sic R5s110175 sic@
  relAspTypeExtension TrCHInfo-r10OrLaterExtensionType OPTIONAL  -- Rel-10 or later @sic R5-130613 R5-134957 R5-145142 sic@
}

--**************************************************************
--
-- CphyTrchConfigReq-TDD
--   To request to configure the transport channel.
--   The same TFCS information should be provided to the PHY and MAC layers at all times. When a CPHY-TrCH-Config-REQ is used to configure the PHY layer, a corresponding CMAC-Config-REQ should be sent to the MAC layer to ensure that the configuration is consistent.
--   HS-DSCH MAC-d flows or E-DCH MAC-d flows shall be separately configured whilst the ulconnectedTrCHList, ulTFCS, dlconnectedTrCHList and dlTFCS are omitted.
--   For configuring MBMS if the default TFCS used in the RRC message the dLTFTS shall use the "complete" CHOICE in "ExplicitTFCS-Configuration " IE and the TFCS configuration shall be in line with clause 14.10.1.1/14.10.1.2 of TS 25.331.
--
--**************************************************************

CphyTrchConfigReq-TDD ::= SEQUENCE {
  activationTime SS-ActivationTime,
  ulconnectedTrCHList SEQUENCE (SIZE (0..maxTrCH)) OF SEQUENCE {
    trchid TransportChannelIdentity,
    ul-TransportChannelType SS-UL-TransportChannelType-TDD, -- @sic R5-134957 R5w130320: TDD TTCN-2/3 differences sic@
    transportChannelInfo CommonOrDedicatedTFS-TDD
  } OPTIONAL,
  ulTFCS TFCS OPTIONAL,
  dlconnectedTrCHList SEQUENCE (SIZE (0..maxTrCH)) OF SEQUENCE {
    trchid TransportChannelIdentity,
    dl-TransportChannelType SS-DL-TransportChannelType,
    transportChannelInfo CommonOrDedicatedTFS-TDD
  } OPTIONAL ,
  dlTFCS TFCS OPTIONAL,
  hsDSCHMacdFlows HS-DSCHMACdFlows-TDD OPTIONAL, -- Rel-5 or later
  e-DCHMacdFlows E-DCHMACdFlows-TDD OPTIONAL,    -- Rel-6 or later
  ehs-DSCH-Flows EHS-DSCH-Flows OPTIONAL,    -- Rel-7 or later
  ehs-DSCH-CommonFlows EHS-DSCH-CommonFlows OPTIONAL,    -- Rel-7 or later
  e-DCHMacd-CommonFlows CommonE-DCHMACdFlows-TDD OPTIONAL, -- Rel-8 or later
  ehs-DSCH-Flows-r9		EHS-DSCH-Flows-r9		OPTIONAL, 	-- Rel-9 or later @sic R5-134957 R5w130320 sic@
  relAspTypeExtension	SEQUENCE {}			OPTIONAL	-- Rel-10 or later @sic R5-134957 sic@

}

--**************************************************************
--
-- CrlcConfigReq
--   To request to setup, re-configure or release RLC entityThe Stop parameter indicates that the RLC entity shall not transmit or receive RLC PDUs. The Continue parameter indicates that the RLC entity shall continue transmission and reception of RLC PDUs. When the RLC entity is stopped, the RLC timers are not affected. Triggered polls and status transmissions are delayed until the RLC entity is continued.
--
--**************************************************************

CrlcConfigReq ::= CHOICE {
  setup RBInfo,
  reconfigure RBInfo,
  release NULL,
  sS-stop NULL,
  sS-continue NULL 
}

--**************************************************************
--
-- CrlcConfigReq-TDD
--   To request to setup, re-configure or release RLC entity The Stop parameter indicates that the RLC entity shall not transmit or receive RLC PDUs. The Continue parameter indicates that the RLC entity shall continue transmission and reception of RLC PDUs. When the RLC entity is stopped, the RLC timers are not affected. Triggered polls and status transmissions are delayed until the RLC entity is continued.
--
--**************************************************************

CrlcConfigReq-TDD ::= CHOICE {
  setup RBInfo-TDD,
  reconfigure RBInfo-TDD,
  release NULL,
  sS-stop NULL,
  sS-continue NULL 
}

--**************************************************************
--
-- DL-DPCHInfo-FDD
--
--**************************************************************

DL-DPCHInfo-FDD ::= SEQUENCE {
  dl-CommonInformation DL-CommonInformation,
  dl-DPCH-InfoPerRL DL-DPCH-InfoPerRL,
  rl-Information RL-Information-FDD
}

--**************************************************************
--
-- DL-DPCHInfo-TDD
--
--**************************************************************

DL-DPCHInfo-TDD ::= SEQUENCE {
  dl-CommonInformation DL-CommonInformation-r4,
  dl-DPCH-InfoPerRL DL-DPCH-InfoPerRL-r4,
  powerOffsetOfTFCI-PO1 INTEGER (0..24),
  powerOffsetOfTPC-PO2 INTEGER (0..24), --@sic R5w140013 sic@
  dl-TxPower DL-TxPower,
  dl-TxPowerMax DL-TxPower,
  dl-TxPowerMin DL-TxPower,
  dL-TimeslotISCPInfoLCR TimeslotListWithISCP-LCR
}

--**************************************************************
--
-- TimeslotListWithISCP-LCR
--
--**************************************************************
TimeslotListWithISCP-LCR ::= SEQUENCE (SIZE (1..maxTS ) ) OF TimeslotWithISCP-LCR

--**************************************************************
--
-- TimeslotWithISCP-LCR
--
--**************************************************************
TimeslotWithISCP-LCR::= SEQUENCE {
  timeslot TimeslotNumber-LCR-r4,
  timeslotISCP TimeslotISCP
}

--**************************************************************
--
-- DL-DPCHInfo-r5-FDD
--   Applicable Rel-5 or later
--
--**************************************************************

DL-DPCHInfo-r5-FDD ::= SEQUENCE    {
  dl-CommonInformation DL-CommonInformation-r5,
  dl-DPCH-InfoPerRL DL-DPCH-InfoPerRL-r5,
  rl-Information RL-Information-FDD
}

--**************************************************************
--
-- DL-DPCHInfo-r5-TDD
--   Applicable Rel-5 or later
--
--**************************************************************

DL-DPCHInfo-r5-TDD ::= SEQUENCE    {
  dl-CommonInformation DL-CommonInformation-r5,
  dl-DPCH-InfoPerRL DL-DPCH-InfoPerRL-r5,
  powerOffsetOfTFCI-PO1 INTEGER (0..24),
  powerOffsetOfTPC-PO2 INTEGER (0..24),
  dl-TxPower DL-TxPower,
  dl-TxPowerMax DL-TxPower,
  dl-TxPowerMin DL-TxPower,
  dL-TimeslotISCPInfoLCR TimeslotListWithISCP-LCR 
}

--**************************************************************
--
-- DL-DPCHInfo-r6-FDD
--   Applicable Rel-6 or later
--
--**************************************************************

DL-DPCHInfo-r6-FDD ::= SEQUENCE {
  dl-CommonInformation DL-CommonInformation-r6,
  dl-Dpch-InfoPerRL CHOICE {
    dl-DPCH-InfoPerRL DL-DPCH-InfoPerRL-r6,
    dl-FDPCH-InfoPerRL DL-FDPCH-InfoPerRL-r6
  },
  rl-Information RL-Information-FDD
}

--**************************************************************
--
-- DL-DPCHInfo-r6-TDD
--   Applicable Rel-6 or later
--
--**************************************************************

DL-DPCHInfo-r6-TDD ::= SEQUENCE {
  dl-CommonInformation DL-CommonInformation-r6,
  dl-Dpch-InfoPerRL CHOICE {
    dl-DPCH-InfoPerRL DL-DPCH-InfoPerRL-r6,
    dl-FDPCH-InfoPerRL DL-FDPCH-InfoPerRL-r6
  },
  rl-Information RL-Information-TDD
}

--**************************************************************
--
-- DL-DPCHInfo-r7-FDD
--   Applicable Rel-7 or later
--
--**************************************************************

DL-DPCHInfo-r7-FDD ::= SEQUENCE {
  dl-CommonInformation DL-CommonInformation-r7,
  dl-Dpch-InfoPerRL CHOICE {
    dl-DPCH-InfoPerRL DL-DPCH-InfoPerRL-r7,
    dl-FDPCH-InfoPerRL DL-FDPCH-InfoPerRL-r7
  },
  rl-Information RL-Information-FDD
}

--**************************************************************
--
-- DL-DPCHInfo-r7-TDD
--   Applicable Rel-7 or later
--
--**************************************************************

DL-DPCHInfo-r7-TDD ::= SEQUENCE {
  dl-CommonInformation DL-CommonInformation-r7,
  dl-Dpch-InfoPerRL CHOICE {
    dl-DPCH-InfoPerRL DL-DPCH-InfoPerRL-r7,
    dl-FDPCH-InfoPerRL DL-FDPCH-InfoPerRL-r7
  },
  rl-Information RL-Information-TDD
}

--**************************************************************
--
-- DL-DPCHInfo-r8-FDD
--   Applicable Rel-8 or later
--
--**************************************************************

DL-DPCHInfo-r8-FDD ::= SEQUENCE {
  dl-CommonInformation DL-CommonInformation-r8,
  dl-Dpch-InfoPerRL CHOICE {
    dl-DPCH-InfoPerRL DL-DPCH-InfoPerRL-r7,
    dl-FDPCH-InfoPerRL DL-FDPCH-InfoPerRL-r7
  },
  rl-Information RL-Information-FDD
}

--**************************************************************
--
-- DL-DPCHInfo-r8-TDD
--   Applicable Rel-8 or later
--
--**************************************************************

DL-DPCHInfo-r8-TDD ::= SEQUENCE {
  dl-CommonInformation DL-CommonInformation-r8,
  dl-Dpch-InfoPerRL CHOICE {
    dl-DPCH-InfoPerRL DL-DPCH-InfoPerRL-r7,
    dl-FDPCH-InfoPerRL DL-FDPCH-InfoPerRL-r7
  },
  rl-Information RL-Information-TDD
}

--**************************************************************
--
-- DL-DPCHInfo-r10-FDD
--   Applicable Rel-10 or later
--
--**************************************************************
DL-DPCHInfo-r10-FDD ::= SEQUENCE {
  dl-CommonInformation DL-CommonInformation-r10,
  dl-Dpch-InfoPerRL CHOICE {
    dl-DPCH-InfoPerRL DL-DPCH-InfoPerRL-r7,
    dl-FDPCH-InfoPerRL DL-FDPCH-InfoPerRL-r7
  },
  rl-Information RL-Information-FDD
}

--**************************************************************
--
-- DL-DPCHInfo-r10-TDD
--   Applicable Rel-10 or later
--
--**************************************************************
DL-DPCHInfo-r10-TDD ::= SEQUENCE {
  dl-CommonInformation DL-CommonInformation-r10,
  dl-Dpch-InfoPerRL CHOICE {
    dl-DPCH-InfoPerRL DL-DPCH-InfoPerRL-r7,
    dl-FDPCH-InfoPerRL DL-FDPCH-InfoPerRL-r7
  },
  rl-Information RL-Information-TDD
}

--**************************************************************
--
-- DL-DPCHInfo-r11-FDD
--   Applicable Rel-11 or later
--
--**************************************************************
DL-DPCHInfo-r11-FDD ::= SEQUENCE	{
	dl-CommonInformation	DL-CommonInformation-r11,
	dl-Dpch-InfoPerRL		CHOICE	{
		dl-DPCH-InfoPerRL		DL-DPCH-InfoPerRL-r7,
		dl-FDPCH-InfoPerRL		DL-FDPCH-InfoPerRL-r7
		},
	rl-Information			RL-Information-FDD
}

--**************************************************************
--
-- DL-DPCHInfo-r12-FDD
--  Applicable Rel-12 or later
--  Used only when DTCH is mapped on DL-DPCH
--**************************************************************
DL-DPCHInfo-r12-FDD ::= SEQUENCE	{
	dl-CommonInformation	DL-CommonInformation-r12,
	dl-Dpch-InfoPerRL		CHOICE	{
		dl-DPCH-InfoPerRL		DL-DPCH-InfoPerRL-r12,
		dl-FDPCH-InfoPerRL		DL-FDPCH-InfoPerRL-r7
		},
	rl-Information			RL-Information-FDD
}

--**************************************************************
--
-- DL-DPCHInfo-r13-FDD
--  Applicable Rel-13 or later
--  Used only when DTCH is mapped on DL-DPCH
-- @sic R5-176156 sic@
--**************************************************************
DL-DPCHInfo-r13-FDD ::= SEQUENCE	{
	dl-CommonInformation	DL-CommonInformation-r12,
	dl-Dpch-InfoPerRL		CHOICE	{
		dl-DPCH-InfoPerRL		DL-DPCH-InfoPerRL-r12,
		dl-FDPCH-InfoPerRL		DL-FDPCH-InfoPerRL-r13
		},
	rl-Information			RL-Information-FDD
}

--**************************************************************
--
-- DL-DPCHInfo-r11-TDD
--   Applicable Rel-11 or later
--
--**************************************************************
DL-DPCHInfo-r11-TDD ::= SEQUENCE	{
	dl-CommonInformation	DL-CommonInformation-r11,
	dl-Dpch-InfoPerRL		CHOICE	{
		dl-DPCH-InfoPerRL		DL-DPCH-InfoPerRL-r7,
		dl-FDPCH-InfoPerRL		DL-FDPCH-InfoPerRL-r7
		},
	rl-Information			RL-Information-TDD
}

--**************************************************************
--
-- DL-DPCHInfo-r12-TDD
--  Applicable Rel-12 or later
--  Used only when DTCH is mapped on DL-DPCH
--**************************************************************
DL-DPCHInfo-r12-TDD ::= SEQUENCE	{
	dl-CommonInformation	DL-CommonInformation-r12,
	dl-Dpch-InfoPerRL		CHOICE	{
		dl-DPCH-InfoPerRL		DL-DPCH-InfoPerRL-r12,
		dl-FDPCH-InfoPerRL		DL-FDPCH-InfoPerRL-r7
		},
	rl-Information			RL-Information-TDD
}


--**************************************************************
--
-- DL-DPCHInfo-r13-TDD
--  Applicable Rel-13 or later
--  Used only when DTCH is mapped on DL-DPCH
-- @sic R5-176156 sic@
--**************************************************************
DL-DPCHInfo-r13-TDD ::= SEQUENCE	{
	dl-CommonInformation	DL-CommonInformation-r12,
	dl-Dpch-InfoPerRL		CHOICE	{
		dl-DPCH-InfoPerRL		DL-DPCH-InfoPerRL-r12,
		dl-FDPCH-InfoPerRL		DL-FDPCH-InfoPerRL-r13
		},
	rl-Information			RL-Information-TDD
}

--**************************************************************
--
-- DL-TxPower
--   Downlink Tx Power relative to PCPICH
--
--**************************************************************

DL-TxPower ::= INTEGER (-35..15)

--**************************************************************
--
-- DwPCH-Power
--   Downlink DwPCH Tx Power,DwPCH-power = power * 10
--   Unit dBm, Range -15dBm .. +40 dBm, Step +0.1dB 
-- TDD
--**************************************************************

DwPCH-Power ::= INTEGER (-150..400)

--**************************************************************
--
-- DL-TxPower-PCPICH
--   Absolute Tx Power of PCPICH
--
--**************************************************************

DL-TxPower-PCPICH ::= INTEGER (-60..-30)

--**************************************************************
--
-- DPCHInfo-FDD
--   The range for powerOffsetOfTPC-PO2 and powerOffsetOfTFCI-PO1 and powerOffsetOfPILOT-PO3 is 0 dB to 6 dB, 0,25 dB per step.
--
--**************************************************************

DPCHInfo-FDD ::= SEQUENCE {
  ul-DPCHInfo UL-DPCH-Info OPTIONAL,
  dl-DPCHInfo DL-DPCHInfo-FDD OPTIONAL
}

--**************************************************************
--
-- DPCHInfo-TDD
--
--**************************************************************

DPCHInfo-TDD ::= SEQUENCE {
  ul-DPCHInfo UL-DPCHInfo-TDD OPTIONAL,
  dl-DPCHInfo DL-DPCHInfo-TDD OPTIONAL
}

--**************************************************************
--
-- UL-DPCHInfo-TDD
--
--**************************************************************

UL-DPCHInfo-TDD ::= SEQUENCE {
  ul-DPCHInfo UL-DPCH-Info-r4
}

--**************************************************************
--
-- DPCHInfo-r5OrLater-FDD
--   Applicable Rel-5 or later
--   At least one of the first two fields ul-DPCHInfo or dl-DPCHInfo shall be present.
--   Presence of hs-DPCCHInd means that the HS-DPCCH shall be configured in the uplink DPCH. If hs-DPCCHInd is absent no HS-DPCCH shall be configured in the uplink DPCH, or the configured HS-DPCCH shall be removed in the modify ASP. In the active set which has radio links from more than one cell the HS-DPCCH is configured only in the HS-DSCH serving cell.
--   Three combinations are valid: ul-DPCH-Info only, dl-DPCHInfo only and ul-DPCH-Info + hs-DPCCHInd.
--   Presence of ss-UL-DPCCH-DRX-Info if UL DPCH being configured and presence of ss-DRX-Info if DL F-DPCH being configured indicates that UL-DTX is enabled.
--   ss-DRX-Info is provided as F-DPCH TPC commands need not be transmitted during gaps due to UL-DPCCH DTX (3GPP TS 25.214 [12], subclause 5.1.2.2.1).
--   ul-DPCH-TimingOffset is the timing offset relative to P-CCPCH, it is provided in Rel-7 only when Enhanced Cell FACH Downlink (common-HS-PDSCH-Info) is configured.
--**************************************************************

DPCHInfo-r5OrLater-FDD ::= CHOICE    {
  r5 SEQUENCE {
    ul-DPCHInfo UL-DPCH-Info-r5 OPTIONAL,
    dl-DPCHInfo DL-DPCHInfo-r5-FDD OPTIONAL,
    hs-DPCCHInd HS-DPCCHInfo OPTIONAL
  },
  r6 SEQUENCE {
    ul-DPCHInfo UL-DPCH-Info-r6 OPTIONAL,
    dl-DPCHInfo DL-DPCHInfo-r6-FDD OPTIONAL,
    hs-DPCCHInd HS-DPCCHInfo OPTIONAL
  },
  r7 SEQUENCE {
    ul-DPCHInfo UL-DPCH-Info-r7 OPTIONAL,
	ul-DPCH-TimingOffset INTEGER (0..38399) OPTIONAL,  
	            -- timing offset relative to P-CCPCH 
				-- applicable to Rel-7 when Enhanced Cell FACH DL is configured
                -- @sic R5-120613 sic@
    dl-DPCHInfo DL-DPCHInfo-r7-FDD OPTIONAL,
    hs-DPCCHInd HS-DPCCHInfo OPTIONAL,
    ss-UL-DPCCH-DRX-Info SS-UL-DPCCH-DRX-Info OPTIONAL,
    ss-DRX-Info DTX-Info OPTIONAL

  },
  r8 SEQUENCE {
    ul-DPCHInfo UL-DPCH-Info-r7 OPTIONAL,
    dl-DPCHInfo DL-DPCHInfo-r8-FDD OPTIONAL,
    hs-DPCCHInd HS-DPCCHInfo-r8 OPTIONAL, -- @sic R5-112477 sic@
    ss-UL-DPCCH-DRX-Info SS-UL-DPCCH-DRX-Info OPTIONAL,
    ss-DRX-Info DTX-Info OPTIONAL
  },
  relAspTypeExtension	DPCHInfo-r10OrLaterExtensionType-FDD
						-- Rel-10 or later @sic R5-130613 R5-134957 sic@
}

--**************************************************************
--
-- DPCHInfo-r10OrLaterExtensionType-FDD
-- Applicable Rel-10 or later
-- rel12-AspExt  is applied whenDTCH is mapped on DL-DPCH
-- @sic R5-130613 R5-133682 R5s150329 R5-176156 sic@ 
--
--**************************************************************
DPCHInfo-r10OrLaterExtensionType-FDD ::= CHOICE {
	rel10-AspExt SEQUENCE	{
		ul-DPCHInfo				UL-DPCH-Info-r7			OPTIONAL,
		dl-DPCHInfo				DL-DPCHInfo-r10-FDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel11-AspExt SEQUENCE	{
		ul-DPCHInfo				UL-DPCH-Info-r11		OPTIONAL,
		dl-DPCHInfo				DL-DPCHInfo-r11-FDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel12-AspExt SEQUENCE	{ -- Rel-12 and later
		ul-DPCHInfo				UL-DPCH-Info-r11		OPTIONAL,
		dl-DPCHInfo				DL-DPCHInfo-r12-FDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel13-AspExt SEQUENCE	{ -- Rel-13 and later
		ul-DPCHInfo				UL-DPCH-Info-r11		OPTIONAL,
		dl-DPCHInfo				DL-DPCHInfo-r13-FDD  	OPTIONAL,
		hs-DPCCHInd				HS-DPCCHInfo-r10		OPTIONAL,
		ss-UL-DPCCH-DRX-Info	SS-UL-DPCCH-DRX-Info	OPTIONAL,
		ss-DRX-Info				DTX-Info				OPTIONAL
	}    
}

--**************************************************************
--
-- DPCHInfo-r5OrLater-TDD
--   Applicable Rel-5 or later
--   At least one of the first two fields ul-DPCHInfo or dl-DPCHInfo shall be present.
--   Presence of hs-DPCCHInd means that the HS-DPCCH shall be configured in the uplink DPCH. If hs-DPCCHInd is absent no HS-DPCCH shall be configured in the uplink DPCH, or the configured HS-DPCCH shall be removed in the modify ASP. In the active set which has radio links from more than one cell the HS-DPCCH is configured only in the HS-DSCH serving cell.
--   Three combinations are valid: ul-DPCH-Info only, dl-DPCHInfo only and ul-DPCH-Info + hs-DPCCHInd.
--
--**************************************************************

DPCHInfo-r5OrLater-TDD ::= CHOICE    {
  r5 SEQUENCE {
    ul-DPCHInfo UL-DPCH-Info-r5 OPTIONAL,
    dl-DPCHInfo DL-DPCHInfo-r5-TDD OPTIONAL,
    hs-DPCCHInd HS-DPCCHInfo OPTIONAL
  },
  r6 SEQUENCE {
    ul-DPCHInfo UL-DPCH-Info-r6 OPTIONAL,
    dl-DPCHInfo DL-DPCHInfo-r6-TDD OPTIONAL,
    hs-DPCCHInd HS-DPCCHInfo OPTIONAL
  },
  r7 SEQUENCE {
    ul-DPCHInfo UL-DPCH-Info-r7 OPTIONAL,
    dl-DPCHInfo DL-DPCHInfo-r7-TDD OPTIONAL,
    hs-DPCCHInd HS-DPCCHInfo OPTIONAL,
    ss-UL-DPCCH-DRX-Info SS-UL-DPCCH-DRX-Info OPTIONAL,
    ss-DRX-Info DTX-Info OPTIONAL

  },
  r8 SEQUENCE {
    ul-DPCHInfo UL-DPCH-Info-r7 OPTIONAL,
    dl-DPCHInfo DL-DPCHInfo-r8-TDD OPTIONAL,
    hs-DPCCHInd HS-DPCCHInfo-r8 OPTIONAL, -- @sic R5-112477 sic@
    ss-UL-DPCCH-DRX-Info SS-UL-DPCCH-DRX-Info OPTIONAL,
    ss-DRX-Info DTX-Info OPTIONAL
  },
  relAspTypeExtension	DPCHInfo-r10OrLaterExtensionType-TDD
}

--**************************************************************
--
-- DPCHInfo-r10OrLaterExtensionType-TDD
-- Applicable Rel-10 or later
-- rel12_AspExt  is applied when DTCH is mapped on DL-DPCH
-- @sic R5-130613 R5-133682 R5s150329 R5-176156 sic@ 
--
--**************************************************************
DPCHInfo-r10OrLaterExtensionType-TDD ::= CHOICE {
	rel10-AspExt SEQUENCE	{
		ul-DPCHInfo				UL-DPCH-Info-r7			OPTIONAL,
		dl-DPCHInfo				DL-DPCHInfo-r10-TDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel11-AspExt SEQUENCE	{
		ul-DPCHInfo				UL-DPCH-Info-r11		OPTIONAL,
		dl-DPCHInfo				DL-DPCHInfo-r11-TDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel12-AspExt SEQUENCE	{ -- Rel-12 and later
		ul-DPCHInfo				UL-DPCH-Info-r11		OPTIONAL,
		dl-DPCHInfo				DL-DPCHInfo-r12-TDD		OPTIONAL,
		hs-DPCCHInd				HS-DPCCHInfo-r10		OPTIONAL,
		ss-UL-DPCCH-DRX-Info	SS-UL-DPCCH-DRX-Info	OPTIONAL,
		ss-DRX-Info				DTX-Info				OPTIONAL
	},
	rel13-AspExt SEQUENCE	{ -- Rel-13 and later
		ul-DPCHInfo				UL-DPCH-Info-r11		OPTIONAL,
		dl-DPCHInfo				DL-DPCHInfo-r13-TDD		OPTIONAL,
		hs-DPCCHInd				HS-DPCCHInfo-r10		OPTIONAL,
		ss-UL-DPCCH-DRX-Info	SS-UL-DPCCH-DRX-Info	OPTIONAL,
		ss-DRX-Info				DTX-Info				OPTIONAL
	}
}

--**************************************************************
--
-- EHS-DSCH-CommonFlows
--   Rel-7 or later
--
--**************************************************************

EHS-DSCH-CommonFlows ::= SEQUENCE {
  harqInfo-r7  HARQ-Info-r7 OPTIONAL,           --@sic R5w140013 sic@
  common-MAC-ehs-ReorderingQueueList SS-Common-MAC-ehs-ReorderingQueueList OPTIONAL
}

--**************************************************************
--
-- EHS-DSCH-Flows
--   Rel-7 or later
--
--**************************************************************

EHS-DSCH-Flows ::= SEQUENCE {
  harqInfo-r7  HARQ-Info-r7 OPTIONAL,          --@sic R5w140013 sic@ 
  addOrReconfMAC-ehs-ReordQ SS-MAC-ehs-AddReconfReordQueueList OPTIONAL,
  ackNackRepetitionFactor ACK-NACK-repetitionFactor OPTIONAL,
  mimoStatus BOOLEAN OPTIONAL
}

--**************************************************************
--
-- EHS-DSCH-Flows-r9
--   Rel-9 or later
--
--**************************************************************

EHS-DSCH-Flows-r9 ::= SEQUENCE {
  harqInfo-r7  HARQ-Info-r7 OPTIONAL,  --@sic R5w140013 sic@         
  addOrReconfMAC-ehs-ReordQ SS-MAC-ehs-AddReconfReordQueueList-r9 OPTIONAL,
  ackNackRepetitionFactor ACK-NACK-repetitionFactor OPTIONAL,
  mimoStatus BOOLEAN OPTIONAL
}

--**************************************************************
--
-- EHS-DSCH-Flows-r11
-- Applicable Rel-11 or later
-- 
--**************************************************************
EHS-DSCH-Flows-r11 ::= SEQUENCE		{
	harqInfo-r11					HARQ-Info-r11				OPTIONAL,
	addOrReconfMAC-ehs-ReordQ		SS-MAC-ehs-AddReconfReordQueueList-r11	OPTIONAL,
	ackNackRepetitionFactor			ACK-NACK-repetitionFactor	OPTIONAL,
	mimoStatus						BOOLEAN						OPTIONAL
}

--**************************************************************
--
-- EHS-DSCH-Flows-r13
-- Applicable Rel-13 or later
-- @sic R5-176156 sic@
-- 
--**************************************************************
EHS-DSCH-Flows-r13 ::= SEQUENCE		{
	harqInfo-r13					HARQ-Info-r13				OPTIONAL,
	dl-MAC-HeaderType	CHOICE {
		mac-hs			SS-AddOrReconfMAC-dFlow,
		mac-ehs			SS-MAC-ehs-AddReconfReordQueueList-r11
	},
	ackNackRepetitionFactor			ACK-NACK-repetitionFactor	OPTIONAL,
	mimoStatus						BOOLEAN						OPTIONAL
}

--**************************************************************
--
-- CommonE-DCHMACdFlows
--   Rel-6 or later
--
--**************************************************************
CommonE-DCHMACdFlows ::= SEQUENCE {
  tti E-DCH-TTI,
  harq-Info ENUMERATED {rv0 (0), rvtable (1)},         
  addReconfMAC-d-FlowList Common-E-DCH-MAC-d-FlowList --@sic R5w140013 sic@
}

CommonE-DCHMACdFlows-TDD ::= SEQUENCE {
  harq-Info ENUMERATED {rv0 (0), rvtable (1)},         
  addReconfMAC-d-FlowList Common-E-DCH-MAC-d-FlowList --@sic R5w140013 sic@
}

--**************************************************************
--
-- E-DCHMACdFlows
--   Rel-6 or later
--
--**************************************************************


E-DCHMACdFlows ::= SEQUENCE {
  tti E-DCH-TTI,
  harq-Info ENUMERATED {rv0 (0), rvtable (1)},         
  addReconf-MAC-d-FlowList E-DCH-AddReconf-MAC-d-FlowList OPTIONAL,
  addReconf-MAC-d-FlowList-r7 E-DCH-AddReconf-MAC-d-FlowList-r7 OPTIONAL
}

--**************************************************************
--
-- E-DCHMACdFlows-TDD
--   Rel-7 or later
--   E-DCHMACdFlows in TTCN-2
-- 
--**************************************************************

E-DCHMACdFlows-TDD ::= SEQUENCE {  
  harq-Info ENUMERATED {rv0 (0), rvtable (1)},         
  addReconf-MAC-d-FlowList-r7 E-DCH-AddReconf-MAC-d-FlowList-r7 OPTIONAL --@sic R5w140013 sic@
}

--**************************************************************
--
-- FrequencyBandFDD
--   The frequency band indicator indicates how to interpret the radio frequency broadcast.
--
--**************************************************************

FrequencyBandFDD ::= CHOICE {
  frequencyBandIndicator RadioFrequencyBandFDD,
  frequencyBandIndicator2 RadioFrequencyBandFDD2,
  frequencyBandIndicator3 RadioFrequencyBandFDD3,
  relAspTypeExtension  SEQUENCE{}  -- @sic R5-130613 R5-134957 sic@

}

--**************************************************************
--
-- HS-DPCCHInfo
--
--**************************************************************

HS-DPCCHInfo ::= SEQUENCE {
  cqi-RepetitionFactor CQI-RepetitionFactor,
  ackNackRepetitionFactor ACK-NACK-repetitionFactor,
  mimoStatus BOOLEAN DEFAULT FALSE
}

--**************************************************************
--
-- HS-DPCCHInfo-r10
-- Applicable to 4C-HSDPA Rel-10 or later 
-- secondaryServing-HS-DSCH-Cell indicates if the HS-DSCH secondary serving cell is activated (see 3GPP TS 25.214 [12], clause 6A.1)
-- The HS-DPCCH code allocation and slot format are set according to 3GPP TS 25.213 [66], clause 4.3.1.2.2.
--**************************************************************

HS-DPCCHInfo-r10 ::= SEQUENCE {
  cqi-RepetitionFactor   CQI-RepetitionFactor,
  ackNackRepetitionFactor   ACK-NACK-repetitionFactor,
  mimoStatus   BOOLEAN	DEFAULT FALSE,
  firstSecondaryServing-HS-DSCH-Cell   ENUMERATED { deactivated (0), activated (1) } DEFAULT deactivated,
  secondSecondaryServing-HS-DSCH-Cell   ENUMERATED { deactivated (0), activated (1) } DEFAULT deactivated,
  thirdSecondaryServing-HS-DSCH-Cell   ENUMERATED { deactivated (0), activated (1) } DEFAULT deactivated  
								-- Relevant when third secondary cell is configured
}

--**************************************************************
--
-- HS-DSCHMACdFlows
--   Applicable Rel-5 or later.
--   Within the ACK/NACK repetition period indicated by ackNackRepetitionFactor the SS shall not transmit MAC-hs PDU's on HS-PDSCH.
--
--**************************************************************

HS-DSCHMACdFlows ::= SEQUENCE {
  harqInfo HARQ-Info OPTIONAL,
  addOrReconfMACdFlow SS-AddOrReconfMAC-dFlow OPTIONAL,
  ackNackRepetitionFactor ACK-NACK-repetitionFactor OPTIONAL,
  harqInfo-r7 HARQ-Info-r7 OPTIONAL
 -- mimoStatus BOOLEAN OPTIONAL No longer in TTCN2 version
}

HS-DSCHMACdFlows-TDD ::= SEQUENCE {
  harqInfo HARQ-Info OPTIONAL,
  addOrReconfMACdFlow SS-AddOrReconfMAC-dFlow OPTIONAL,
  harqInfo-r7 HARQ-Info-r7 OPTIONAL
 -- mimoStatus BOOLEAN OPTIONAL No longer in TTCN2 version
}


--**************************************************************
--
-- HS-PDSCHInfo-r5OrLater
--   Applicable Rel-5 or later
--   When CHY-RL-Setup-REQ is called with CHOICE of hS-PDSCHInfo HS-PDSCH and HS-SCCH shall be configured in SS.
--   The following HS-DSCH related parameters are passed to the SS implicitly by HSDSCH-physical-layer-category:
--    - Maximum number of HS-DSCH codes can be received by UE,
--    - Minimum inter-TTI interval,
--    - Maximum number of bits of an HS-DSCH transport block within an HS-DSCH TTI
--    - Total number of soft channel bits".
--   HSDSCH-physical-Layer-category is also used for interpretation of the meaning of CQI value.
--
--**************************************************************

HS-PDSCHInfo-r5OrLater-FDD ::= CHOICE {
  r5 SEQUENCE {
    hSDSCHPhysicalLayerCategory HSDSCH-physical-layer-category,
    h-RNTI H-RNTI,
    dlHSPDSCHInformation DL-HSPDSCH-Information,
    sttd-Indicator BOOLEAN,
    hs-SCCH-TxPower DL-TxPower, -- offset related to CPICH
--    hs-PDSCHChannelisationCodeInfo SEQUENCE (SIZE (1..maxPDSCHtimeslot ) ) OF HS-PDSCH-ChannelisationCodeInfo-LCR OPTIONAL, @sic R5-112477r1 sic@
    hs-DPCCHToFollow BOOLEAN DEFAULT TRUE
  },
  r6 SEQUENCE {
    hSDSCHPhysicalLayerCategory HSDSCH-physical-layer-category,
    h-RNTI H-RNTI,
    dlHSPDSCHInformation DL-HSPDSCH-Information-r6,
    sttd-Indicator BOOLEAN,
    hs-SCCH-TxPower DL-TxPower, -- offset related to CPICH
--    hs-PDSCHChannelisationCodeInfo SEQUENCE (SIZE (1..maxPDSCHtimeslot ) ) OF HS-PDSCH-ChannelisationCodeInfo-LCR OPTIONAL, @sic R5-112477r1 sic@
    hs-DPCCHToFollow BOOLEAN DEFAULT TRUE
  },
  r7 HS-PDSCHInfo-r7-FDD,
  r8 HS-PDSCHInfo-r8-FDD,
  r9 HS-PDSCHInfo-r9-FDD,   -- @sic R5s110175 sic@
  relAspTypeExtension HS-PDSCHInfo-r10OrLaterExtensionType	-- Rel-10 or later @sic R5-130613 R5-134957 sic@
}

HS-PDSCHInfo-r5OrLater-TDD ::= CHOICE {
  r5 SEQUENCE {
    hSDSCHPhysicalLayerCategory HSDSCH-physical-layer-category,
    h-RNTI H-RNTI,
    dlHSPDSCHInformation DL-HSPDSCH-Information,
    sttd-Indicator BOOLEAN,
    hs-SCCH-TxPower DL-TxPower, -- offset related to CPICH
    hs-PDSCHChannelisationCodeInfo SEQUENCE (SIZE (1..maxPDSCHtimeslot ) ) OF HS-PDSCH-ChannelisationCodeInfo-LCR, --@sic R5-112477r1 sic@
    hs-DPCCHToFollow BOOLEAN DEFAULT TRUE
  },
  r6 SEQUENCE {
    hSDSCHPhysicalLayerCategory HSDSCH-physical-layer-category,
    h-RNTI H-RNTI,
    dlHSPDSCHInformation DL-HSPDSCH-Information-r6,
    sttd-Indicator BOOLEAN,
    hs-SCCH-TxPower DL-TxPower, -- offset related to CPICH
    hs-PDSCHChannelisationCodeInfo SEQUENCE (SIZE (1..maxPDSCHtimeslot ) ) OF HS-PDSCH-ChannelisationCodeInfo-LCR, --@sic R5-112477r1 sic@
    hs-DPCCHToFollow BOOLEAN DEFAULT TRUE
  },
  r7 HS-PDSCHInfo-r7-TDD,
  r8 HS-PDSCHInfo-r8-TDD,
  r9 HS-PDSCHInfo-r9-TDD,   -- @sic R5s110175 sic@
  relAspTypeExtension SEQUENCE{} -- Rel-10 or later   @sic R5-134957 sic@
}

--**************************************************************
--
-- HS-PDSCHInfo-r10OrLaterExtensionType
-- Rel-10 or later
-- hS-PDSCH-Info rel10 extension is applied to 4C HSDPA configurations.
-- The IEs related to HS-DSCH physical layer vategories are mutually exclusive. One of the IE shall be present in the SS configuration. 
-- The IE "hsdsch-physical-layer-category-ext4" is present  when 2 secondary cells are configured. 
-- The IE "hsdsch-physical-layer-category-ext5" is present when 3 secondary cells are configured.
-- The IE "hsdsch-physical-layer-category-ext6" is present when multi-cell operation on 5 or 6 cells are configured.
-- The IE "hsdsch-physical-layer-category-ext7" is present when multi-cell operation on 7 or 8 cells are configured.
-- The IE "hsdsch-physical-layer-category-ext8" is present when MIMO with 4 transmit antenna are configured. 
-- @sic R5s150329 sic@
--**************************************************************
HS-PDSCHInfo-r10OrLaterExtensionType ::= CHOICE {
	rel10-AspExt SEQUENCE	{
		hSDSCHPhysicalLayerCategory	HSDSCH-physical-layer-category OPTIONAL,
		hsdsch-physical-layer-category-ext	HSDSCH-physical-layer-category-ext OPTIONAL,
		hsdsch-physical-layer-category-ext2	
									HSDSCH-physical-layer-category-ext2 OPTIONAL,
		hsdsch-physical-layer-category-ext3 
									HSDSCH-physical-layer-category-ext3  OPTIONAL,
		hsdsch-physical-layer-category-ext4 
									HSDSCH-physical-layer-category-ext4  OPTIONAL,
		hsdsch-physical-layer-category-ext5 
									HSDSCH-physical-layer-category-ext5  OPTIONAL,
		h-RNTI						H-RNTI,
		dlHSPDSCHInformation		DL-HSPDSCH-Information-r9,
		sttd-Indicator				BOOLEAN,
		hs-SCCH-TxPower				DL-TxPower,	-- offset related to CPICH
		ss-DTX-Info					DRX-Info	OPTIONAL,
		hs-scch-LessInfo			HS-SCCH-LessInfo-r7		OPTIONAL,
		mimo-Parameters				MIMO-Parameters-r9		OPTIONAL,
		hs-DPCCHToFollow			BOOLEAN	DEFAULT TRUE,
		hs-SCCH-SttdIndicator		BOOLEAN DEFAULT FALSE
	},
	rel11-AspExt SEQUENCE	{
		hSDSCHPhysicalLayerCategory	HSDSCH-physical-layer-category OPTIONAL,
		hsdsch-physical-layer-category-ext
									HSDSCH-physical-layer-category-ext OPTIONAL,
		hsdsch-physical-layer-category-ext2
									HSDSCH-physical-layer-category-ext2 OPTIONAL,
		hsdsch-physical-layer-category-ext3
									HSDSCH-physical-layer-category-ext3  OPTIONAL,
		hsdsch-physical-layer-category-ext4
									HSDSCH-physical-layer-category-ext4  OPTIONAL,
		hsdsch-physical-layer-category-ext5
									HSDSCH-physical-layer-category-ext5  OPTIONAL,
		hsdsch-physical-layer-category-ext6
									HSDSCH-physical-layer-category-ext6	OPTIONAL,
		hsdsch-physical-layer-category-ext7
									HSDSCH-physical-layer-category-ext7	OPTIONAL,
		hsdsch-physical-layer-category-ext8
									HSDSCH-physical-layer-category-ext8	OPTIONAL,
		h-RNTI						H-RNTI,
		dlHSPDSCHInformation		DL-HSPDSCH-Information-r11,
		sttd-Indicator				BOOLEAN,
		hs-SCCH-TxPower				DL-TxPower,	-- offset related to CPICH
		ss-DTX-Info					DRX-Info	OPTIONAL,
		hs-scch-LessInfo			HS-SCCH-LessInfo-r7		OPTIONAL,
		mimo-Parameters				MIMO-Parameters-r9		OPTIONAL,
		hs-DPCCHToFollow			BOOLEAN	DEFAULT TRUE,
		hs-SCCH-SttdIndicator		BOOLEAN DEFAULT FALSE
	},
	commonRel11-AspExt SEQUENCE	{  -- @sic R5-150125 feFACH sic@
		hsdsch-physical-layer-category-ext
									HSDSCH-physical-layer-category-ext, --@sic R5-160942 sic@
		commonOrDedicated-H-RNTI	H-RNTI	OPTIONAL,
		bcchSpecific-H-RNTI			H-RNTI,
		hs-scch-SystemInfo			HS-SCCH-SystemInfo,
		hs-dsch-PagingSystemInformation	HS-DSCH-PagingSystemInformation	OPTIONAL,
		sttd-Indicator				BOOLEAN,
		hs-SCCH-TxPower				DL-TxPower,	-- offset related to CPICH
		hs-DPCCHToFollow			BOOLEAN	DEFAULT TRUE,
		ss-HS-DSCH-DtxCellFach		HS-DSCH-DrxCellfach-info OPTIONAL,
        ss-HS-DSCH-DtxCellFach-SecondDtx    HS-DSCH-DrxCellfach-SecondDrx-info OPTIONAL
	},
	rel12-AspExt SEQUENCE	{		-- Rel-12 or later
		hSDSCHPhysicalLayerCategory	HSDSCH-physical-layer-category OPTIONAL,
		hsdsch-physical-layer-category-ext
									HSDSCH-physical-layer-category-ext OPTIONAL,
		hsdsch-physical-layer-category-ext2
									HSDSCH-physical-layer-category-ext2 OPTIONAL,
		hsdsch-physical-layer-category-ext3
									HSDSCH-physical-layer-category-ext3  OPTIONAL,
		hsdsch-physical-layer-category-ext4
									HSDSCH-physical-layer-category-ext4  OPTIONAL,
		hsdsch-physical-layer-category-ext5
									HSDSCH-physical-layer-category-ext5  OPTIONAL,
		hsdsch-physical-layer-category-ext6
									HSDSCH-physical-layer-category-ext6	OPTIONAL,
		hsdsch-physical-layer-category-ext7
									HSDSCH-physical-layer-category-ext7	OPTIONAL,
		hsdsch-physical-layer-category-ext8
									HSDSCH-physical-layer-category-ext8	OPTIONAL,
		h-RNTI						H-RNTI,
		dlHSPDSCHInformation		DL-HSPDSCH-Information-r12,
		sttd-Indicator				BOOLEAN,
		hs-SCCH-TxPower				DL-TxPower,	-- offset related to CPICH
		ss-DTX-Info					DRX-Info-r12			OPTIONAL,
		hs-scch-LessInfo			HS-SCCH-LessInfo-r7	OPTIONAL,
		mimo-Parameters				MIMO-Parameters-r9	OPTIONAL,
		hs-DPCCHToFollow			BOOLEAN	DEFAULT TRUE,
		hs-SCCH-SttdIndicator		BOOLEAN DEFAULT FALSE
	}
}

--**************************************************************
--
-- HS-PDSCH-ChannelisationCodeInfo-LCR
--
--**************************************************************

HS-PDSCH-ChannelisationCodeInfo-LCR ::= SEQUENCE {
  timeslotNumber TimeslotNumber-LCR-r4,
  startCode HS-ChannelisationCode-LCR,
  stopCode HS-ChannelisationCode-LCR
}


--**************************************************************
--
-- HS-PDSCHInfo-r7
--
--**************************************************************

HS-PDSCHInfo-r7-FDD ::= CHOICE {
  hS-PDSCH-Info SEQUENCE {
    hSDSCHPhysicalLayerCategory HSDSCH-physical-layer-category OPTIONAL,
    hsdsch-physical-layer-category-ext HSDSCH-physical-layer-category-ext OPTIONAL,
    h-RNTI H-RNTI,
    dlHSPDSCHInformation DL-HSPDSCH-Information-r7,
    sttd-Indicator BOOLEAN,
    hs-SCCH-TxPower DL-TxPower, -- offset related to CPICH
--    hs-PDSCHChannelisationCodeInfo SEQUENCE (SIZE (1..maxPDSCHtimeslot ) ) OF HS-PDSCH-ChannelisationCodeInfo-LCR OPTIONAL, @sic R5-112477r1 sic@
    ss-DTX-Info DRX-Info OPTIONAL,
    hs-scch-LessInfo HS-SCCH-LessInfo-r7 OPTIONAL,
    mimo-Parameters MIMO-Parameters-r7 OPTIONAL,
    hs-DPCCHToFollow BOOLEAN DEFAULT TRUE,
	hs-SCCH-SttdIndicator BOOLEAN DEFAULT FALSE  -- @sic R5-120613 sic@

  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo HS-SCCH-SystemInfo,
    hs-dsch-PagingSystemInformation HS-DSCH-PagingSystemInformation OPTIONAL,
    sttd-Indicator BOOLEAN,
    hs-SCCH-TxPower DL-TxPower, -- offset related to CPICH
    hs-DPCCHToFollow BOOLEAN DEFAULT TRUE
  },
  spare2 SEQUENCE {},
  spare3 SEQUENCE {}
}

HS-PDSCHInfo-r7-TDD ::= CHOICE {
  hS-PDSCH-Info SEQUENCE {
    hSDSCHPhysicalLayerCategory HSDSCH-physical-layer-category OPTIONAL,
    hsdsch-physical-layer-category-ext HSDSCH-physical-layer-category-ext OPTIONAL,
    h-RNTI H-RNTI,
    dlHSPDSCHInformation DL-HSPDSCH-Information-r7,
    sttd-Indicator BOOLEAN,
    hs-SCCH-TxPower DL-TxPower, -- offset related to CPICH
    hs-PDSCHChannelisationCodeInfo SEQUENCE (SIZE (1..maxPDSCHtimeslot ) ) OF HS-PDSCH-ChannelisationCodeInfo-LCR, --@sic R5-112477r1 sic@
    ss-DTX-Info DRX-Info OPTIONAL,
    mimo-Parameters MIMO-Parameters-r7 OPTIONAL,
    hs-DPCCHToFollow BOOLEAN DEFAULT TRUE
  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo HS-SCCH-SystemInfo,
    hs-dsch-PagingSystemInformation HS-DSCH-PagingSystemInformation OPTIONAL,
    sttd-Indicator BOOLEAN,
    hs-SCCH-TxPower DL-TxPower, -- offset related to CPICH
    hs-DPCCHToFollow BOOLEAN DEFAULT TRUE
  },
  spare2 SEQUENCE {},
  spare3 SEQUENCE {}
}


--**************************************************************
--
-- HS-PDSCHInfo-r8-FDD
--
--**************************************************************

HS-PDSCHInfo-r8-FDD ::= CHOICE {
  hS-PDSCH-Info SEQUENCE {
    hSDSCHPhysicalLayerCategory HSDSCH-physical-layer-category OPTIONAL,
    hsdsch-physical-layer-category-ext HSDSCH-physical-layer-category-ext OPTIONAL,
    hsdsch-physical-layer-category-ext2 HSDSCH-physical-layer-category-ext2 OPTIONAL,
    h-RNTI H-RNTI,
    dlHSPDSCHInformation DL-HSPDSCH-Information-r8,
    sttd-Indicator BOOLEAN,
    hs-SCCH-TxPower DL-TxPower, -- offset related to CPICH    
--    hs-PDSCHChannelisationCodeInfo SEQUENCE (SIZE (1..maxPDSCHtimeslot ) ) OF HS-PDSCH-ChannelisationCodeInfo-LCR OPTIONAL, @sic R5-112477r1 sic@
    ss-DTX-Info DRX-Info OPTIONAL,
    hs-scch-LessInfo HS-SCCH-LessInfo-r7 OPTIONAL,
    mimo-Parameters MIMO-Parameters-r8 OPTIONAL,
    hs-DPCCHToFollow BOOLEAN DEFAULT TRUE,
	hs-SCCH-SttdIndicator BOOLEAN DEFAULT FALSE  -- @sic R5-120613 sic@
  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo HS-SCCH-SystemInfo,
    hs-dsch-PagingSystemInformation HS-DSCH-PagingSystemInformation OPTIONAL,
    sttd-Indicator BOOLEAN,
    hs-SCCH-TxPower DL-TxPower, -- offset related to CPICH
    hs-DPCCHToFollow BOOLEAN DEFAULT TRUE,
    ss-HS-DSCH-DtxCellFach   HS-DSCH-DrxCellfach-info OPTIONAL 
  },
  spare2 SEQUENCE {},
  spare3 SEQUENCE {}
}

--**************************************************************
--
-- HS-PDSCHInfo-r8-TDD
--
--**************************************************************

HS-PDSCHInfo-r8-TDD ::= CHOICE {
  hS-PDSCH-Info SEQUENCE {
    hSDSCHPhysicalLayerCategory HSDSCH-physical-layer-category OPTIONAL,
    hsdsch-physical-layer-category-ext HSDSCH-physical-layer-category-ext OPTIONAL,
    multiCarrier-physical-layer-category	MultiCarrier-HSDSCH-physical-layer-category	OPTIONAL,
    multiCarrier-physicallayer-category-extension   MultiCarrier-HSDSCH-physical-layer-category-extension	OPTIONAL,
    h-RNTI H-RNTI,
    dlHSPDSCHInformation DL-HSPDSCH-Information-r8,
    sttd-Indicator BOOLEAN,
    hs-SCCH-TxPower DL-TxPower, -- offset related to CPICH    
    mimo-Parameters  MIMO-Parameters-r8		OPTIONAL,
    hs-PDSCHChannelisationCodeInfo SEQUENCE (SIZE (1..maxPDSCHtimeslot ) ) OF HS-PDSCH-ChannelisationCodeInfo-LCR, --@sic R5-140315 sic@
    hs-DPCCHToFollow  BOOLEAN	DEFAULT TRUE,
    controlChannelDRXInfo-TDD128	ControlChannelDRXInfo-TDD128-r8		OPTIONAL,
    sps-Information-TDD128 SPS-Information-TDD128-r8			OPTIONAL

  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo-tdd128 HS-SCCH-SystemInfo-TDD128 OPTIONAL,
    hs-pdsch-MidambleConfiguration	HS-PDSCH-Midamble-Configuration-TDD128 OPTIONAL,
    hs-dsch-PagingSystemInformation-tdd128	HS-DSCH-PagingSystemInformation-TDD128	OPTIONAL,
    sttd-Indicator BOOLEAN,
    hs-SCCH-TxPower DL-TxPower, -- offset related to CPICH
    hs-DPCCHToFollow BOOLEAN DEFAULT TRUE,
    ss-HS-DSCH-DtxCellFach   HS-DSCH-DrxCellfach-info-TDD128  OPTIONAL 
  },
  spare2 SEQUENCE {},
  spare3 SEQUENCE {}
}

--**************************************************************
--
-- HS-PDSCHInfo-r9-FDD
--
--**************************************************************

HS-PDSCHInfo-r9-FDD ::= CHOICE {
  hS-PDSCH-Info SEQUENCE {
    hSDSCHPhysicalLayerCategory HSDSCH-physical-layer-category OPTIONAL,
    hsdsch-physical-layer-category-ext HSDSCH-physical-layer-category-ext OPTIONAL,
    hsdsch-physical-layer-category-ext2 HSDSCH-physical-layer-category-ext2 OPTIONAL,
    hsdsch-physical-layer-category-ext3 HSDSCH-physical-layer-category-ext3 OPTIONAL,
    h-RNTI H-RNTI,
    dlHSPDSCHInformation DL-HSPDSCH-Information-r9,
    sttd-Indicator BOOLEAN,
    hs-SCCH-TxPower DL-TxPower, -- offset related to CPICH
--    hs-PDSCHChannelisationCodeInfo SEQUENCE (SIZE (1..maxPDSCHtimeslot ) ) OF HS-PDSCH-ChannelisationCodeInfo-LCR OPTIONAL, @sic R5-112477r1 sic@
    ss-DTX-Info DRX-Info OPTIONAL,
    hs-scch-LessInfo HS-SCCH-LessInfo-r7 OPTIONAL,
    mimo-Parameters MIMO-Parameters-r9 OPTIONAL,
    hs-DPCCHToFollow BOOLEAN DEFAULT TRUE,
	hs-SCCH-SttdIndicator BOOLEAN DEFAULT FALSE  -- @sic R5-120613 sic@
  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo HS-SCCH-SystemInfo,
    hs-dsch-PagingSystemInformation HS-DSCH-PagingSystemInformation OPTIONAL,
    sttd-Indicator BOOLEAN,
    hs-SCCH-TxPower DL-TxPower, -- offset related to CPICH
    hs-DPCCHToFollow BOOLEAN DEFAULT TRUE,
    ss-HS-DSCH-DtxCellFach   HS-DSCH-DrxCellfach-info OPTIONAL 
  },
  spare2 SEQUENCE {},
  spare3 SEQUENCE {}
}

--**************************************************************
--
-- HS-PDSCHInfo-r9-TDD
--   Applicable Rel-9 or later.
--   Choice of hS-PDSCH-Info will be used for configuring HSD-DSCH with 64QAM and/or CPC.
--   Choice of common-HS-PDSCH-Info will be used for Enhanced Cell-FACH.
--   commonOrDedicated-H-RNTI indicates, the H-RNTI that will be used by UE (either dedicated H-RNTI if provided in RRC message, or selected common H-RNTI transmitted in SIB5).
--   The transmission of BCCH on HS-DSCH is performed by using BCCH specific H-RNTI on the first indexed HS-SCCH code indicated in system information broadcast.
--   Presence of controlChannelDRXInfo-TDD128 makes DL DRX to be enabled.
--   Presence of sps-Information-TDD128 makes SPS operation enabled.
--   Presence of mimo-Parameters indicate MIMO is to be started.
--   The IEs 'hSDSCHPhysicalLayerCategory', 'hsdsch-physical-layer-category-ext', are mutually exclusive. One of the IE shall be present in the SS configuration. The IE If commonOrDedicated-H-RNTI  is omitted, HS-SCCHless is to be applied.
--   If hs-DPCCHToFollow is FALSE, the hs-DPCCHInd IE shall not be present when ul-DPCHInfo is configured or reconfigured. 
--   Presence of ss-HS-DSCH-DtxCellFach makes HS-DSCH DRX operation enabled and SS shall transmit any requested HS-SCCH and HS-DSCH only in occasions when UE will be listening. 
--   hs-PDSCHChannelisationCodeInfo present in TDD configurations. 
--   If tS0-Indicator is TRUE, the bit xts,1 of Time slot information in HS-SCCH carries the information for timeslot 0.
--**************************************************************

HS-PDSCHInfo-r9-TDD ::= CHOICE {
  hS-PDSCH-Info SEQUENCE {
    hSDSCHPhysicalLayerCategory HSDSCH-physical-layer-category OPTIONAL,
    hsdsch-physical-layer-category-ext HSDSCH-physical-layer-category-ext OPTIONAL,
    multiCarrier-physical-layer-category	MultiCarrier-HSDSCH-physical-layer-category	OPTIONAL,
    multiCarrier-physicallayer-category-extension   MultiCarrier-HSDSCH-physical-layer-category-extension	OPTIONAL,
    h-RNTI H-RNTI,
    dlHSPDSCHInformation DL-HSPDSCH-Information-r9,
    sttd-Indicator BOOLEAN,
    hs-SCCH-TxPower DL-TxPower, -- offset related to CPICH    
    mimo-Parameters  MIMO-Parameters-r9		OPTIONAL,
    hs-PDSCHChannelisationCodeInfo SEQUENCE (SIZE (1..maxPDSCHtimeslot ) ) OF HS-PDSCH-ChannelisationCodeInfo-LCR, --@sic R5-140315 sic@
    hs-DPCCHToFollow  BOOLEAN	DEFAULT TRUE,
    controlChannelDRXInfo-TDD128	ControlChannelDRXInfo-TDD128-r8		OPTIONAL,
    sps-Information-TDD128 SPS-Information-TDD128-r8			OPTIONAL
  },
  common-HS-PDSCH-Info SEQUENCE {
    hsdsch-physical-layer-category-ext HSDSCH-physical-layer-category-ext, -- @sic R5-112477 sic@
    commonOrDedicated-H-RNTI H-RNTI OPTIONAL, -- @sic R5-112477 sic@
    bcchSpecific-H-RNTI H-RNTI,
    hs-scch-SystemInfo-tdd128 HS-SCCH-SystemInfo-TDD128 OPTIONAL,
    hs-pdsch-MidambleConfiguration	HS-PDSCH-Midamble-Configuration-TDD128 OPTIONAL,
    hs-dsch-PagingSystemInformation-tdd128	HS-DSCH-PagingSystemInformation-TDD128	OPTIONAL,
    sttd-Indicator BOOLEAN,
    hs-SCCH-TxPower DL-TxPower, -- offset related to CPICH
    hs-DPCCHToFollow BOOLEAN DEFAULT TRUE,
    ss-HS-DSCH-DtxCellFach   HS-DSCH-DrxCellfach-info-TDD128  OPTIONAL 
  },
  spare2 SEQUENCE {},
  spare3 SEQUENCE {}
}

--**************************************************************
--
-- HyperFrameNumber
--
--**************************************************************

HyperFrameNumber ::= BIT STRING (SIZE (20))

--**************************************************************
--
-- IP-VersionType
--
--**************************************************************

IP-VersionType ::= ENUMERATED { iPv4(0), iPv6(1) }

--**************************************************************
--
-- Increment-Mode
--
--**************************************************************

Increment-Mode ::= ENUMERATED {incPerCFN-Cycle(0), notInc(1), incByOne-IncPerCFN-Cycle(2)}

--**************************************************************
--
-- IntegrityActivationInfo
--   Comment    DL or UL integrity activation info.At the RRC message sequence numbers specified in the ul-IntegProtActivationInfo the SS shall initialise COUNT-I for the SRB's indicated in the ul-IntegProtActivationInfo and start using the new configuration on uplink for the indicated SRB's.If the START value is omitted in the CRLC-SecurityMode-Config-REQ above COUNT-I initialisation shall not be performed.
--   Type Definition
--
--**************************************************************

IntegrityActivationInfo ::= CHOICE {
  integrityProtectionModeInfo IntegrityProtectionModeInfo,
  ul-IntegProtActivationInfo IntegrityProtActivationInfoList,
  integrityProtectionModeInfo-r7 IntegrityProtectionModeInfo-r7
}

--**************************************************************
--
-- IntegrityProtActivationInfoList
--   List of SS IntegrityProtActivationInfo
--
--**************************************************************

IntegrityProtActivationInfoList ::= SEQUENCE (SIZE (1..maxRB ) ) OF SS-IntegrityProtActivationTimeInfo

--**************************************************************
--
-- IntegrityResult
--
--**************************************************************

IntegrityResult ::= CHOICE {
  integrityNotUsed NULL,
  integrityUsed IntegrityStatus
}

--**************************************************************
--
-- IntegrityStatus
--
--**************************************************************

IntegrityStatus ::= ENUMERATED {
  i-pass(0),
  i-fail(1)
}

--**************************************************************
--
-- KeyCiphering
--
--**************************************************************

KeyCiphering ::= BIT STRING (SIZE (128))

--**************************************************************
--
-- SS-LogicalChannelList
--
--**************************************************************

SS-LogicalChannelList ::= CHOICE
{
  allSizes NULL,
  configured NULL,
  explicitList SEQUENCE (SIZE (1..15)) OF SS-LogicalChannelByRB
}

--**************************************************************
--
-- SS-LogicalChannelByRB
--
--**************************************************************

SS-LogicalChannelByRB ::= SEQUENCE
{
  rb-Identity INTEGER  (-31..32),
  logChOfRb INTEGER (0..1) OPTIONAL
}

--**************************************************************
--
-- LogicalChannelType
--
--**************************************************************

LogicalChannelType ::= ENUMERATED
{
  bCCH (0),
  pCCH (1),
  cCCH (2),
  cTCH (3),
  dCCH (4),
  dTCH (5),
  sHCCH (6),
  mTCH (7),
  mCCH (8),
  mSCH (9) 
}

--**************************************************************
--
-- MAC-HeaderManipulation
--
--**************************************************************

MAC-HeaderManipulation ::= ENUMERATED
{
  normalMacHeader (0),
  omitMacHeader (1)
}

--**************************************************************
--
-- MimoAntennaConfigType
--
--**************************************************************

MimoAntennaConfigType ::= ENUMERATED 
{
  noMimo(0), 
  antenna2pCPICH(1), 
  antenna2sCPICH(2), 
  spare(3) 
}

--**************************************************************
--
-- Mui
--
--**************************************************************

Mui ::= INTEGER (0..4095)

--**************************************************************
--
-- PDSCHInfo-FDD
--
--**************************************************************

PDSCHInfo-FDD ::= SEQUENCE {
  fdd-tdd CHOICE    {
    fdd SEQUENCE {
      pdsch-CodeMapping PDSCH-CodeMapping
    } ,
    tdd SEQUENCE { -- TDD not applicable @sic R5-130314 sic@
    }
  },
  dl-TxPower DL-TxPower
}

--**************************************************************
--
-- PDSCHInfo-TDD
--
--**************************************************************

PDSCHInfo-TDD ::= SEQUENCE {
  pdsch-Identity PDSCH-Identity,
  pdsch-Info PDSCH-Info-r4,
  pdsch-PowerControlInfo PDSCH-PowerControlInfo OPTIONAL,
  dl-TxPower DL-TxPower
}

--**************************************************************
--
-- PUSCHInfo
-- TDD
--**************************************************************

PUSCHInfo ::= SEQUENCE {
  pusch-Identity              PUSCH-Identity,
  pusch-Info                  PUSCH-Info-r4,
  pusch-PowerControlInfo      PUSCH-PowerControlInfo-r4 OPTIONAL
}

--**************************************************************
--
-- PICHInfo-FDD
--
--**************************************************************

PICHInfo-FDD ::= SEQUENCE {
  pichinfo PICH-Info,
  dl-TxPower PICH-PowerOffset,
  sccpchId-associated INTEGER (0..32)
}

--**************************************************************
--
-- PICHInfo-TDD
--
--**************************************************************

PICHInfo-TDD ::= SEQUENCE {
  pichinfo PICH-Info-LCR-r4,
  dl-TxPower PICH-PowerOffset,
  sccpchId-associated INTEGER (0..32)
}

--**************************************************************
--
-- PRACHInfo-FDD
--
--**************************************************************

PRACHInfo-FDD ::= SEQUENCE {
  fdd-tdd CHOICE {
    fdd SEQUENCE {
      preambleSignature AvailableSignatures,
      spreadingFactorForDataPart SF-PRACH,
      preambleScramblingCode PreambleScramblingCodeWordNumber,
      puncturingLimit PuncturingLimit,
      accessSlot AvailableSubChannelNumbers
    },
    tdd SEQUENCE {  -- TDD not applicable @sic R5-140314 sic@
    },
    fdd-prachForEnhUL SEQUENCE {			-- Rel-8 or later
	   -- For rel-99 PRACH
	   preambleSignature				AvailableSignatures,
  	   spreadingFactorForDataPart		SF-PRACH,
	   preambleScramblingCode			PreambleScramblingCodeWordNumber,
   	   puncturingLimit					PuncturingLimit,
		accessSlot						AvailableSubChannelNumbers,

		-- For for Enhanced Uplink E-DCH transmission
		commonEDCH-PreambleSignature	AvailableSignatures, 
		-- access preamble signature for E-DCH transmission
		commonEDCH-PreambleScramblingCode	PreambleScramblingCodeWordNumber,
		commonEDCH-AccessSlot			AvailableSubChannelNumbers
	}

  }
}

--**************************************************************
--
-- PRACHInfo-TDD
--
--**************************************************************

PRACHInfo-TDD ::= SEQUENCE {
  pRACH-RACH-Info-LCR-r4 PRACH-RACH-Info-LCR-r4,
  accessServiceClass-TDD-LCR AccessServiceClass-TDD-LCR-r4,
  fPACH-Power DL-TxPower
}

--**************************************************************
--
-- PayloadSize
--
--**************************************************************

PayloadSize ::= INTEGER (0..4992)

--**************************************************************
--
-- PhysicalChannelIdentity
--
--**************************************************************

PhysicalChannelIdentity ::= INTEGER (0..31)

--**************************************************************
--
-- PrimaryCCPCHInfo-FDD
--
--**************************************************************

PrimaryCCPCHInfo-FDD ::= SEQUENCE {
  sttd-Indicator BOOLEAN,
  dl-TxPower DL-TxPower
  -- timeSlot TimeSlot OPTIONAL,
  -- burstType BurstType OPTIONAL,
  -- offset Offset OPTIONAL,
  -- repetitionPeriod RepetitionPeriod OPTIONAL,
  -- repetitionLength RepetitionLength OPTIONAL,
}

--**************************************************************
--
-- PrimaryCCPCHInfo-TDD
--
--**************************************************************

PrimaryCCPCHInfo-TDD ::= SEQUENCE {
  sctd-Indicator ENUMERATED {notApplied(0),applied(1)},
  tstd-Indicator ENUMERATED {notApplied(0),applied(1)},
  commonTimeSlotInfo CommonTimeslotInfo,
  dL-TxPower-PCCPCH DL-TxPower-PCCPCH,
  relAspTypeExtension 	SEQUENCE{} OPTIONAL -- Rel-10 or later  @sic R5-134957 sic@
}
--**************************************************************
--
-- PrimaryCPICHInfo
--
--**************************************************************

PrimaryCPICHInfo ::= SEQUENCE {
  dl-TxPower-PCPICH DL-TxPower-PCPICH,
  txdiversityIndicator BOOLEAN,
  mimoAntenna2CPICH MimoAntennaConfigType DEFAULT noMimo,
  dC-SecondaryServingCell BOOLEAN DEFAULT FALSE,   -- Rel-8 or later
  relAspTypeExtension  SEQUENCE{}  OPTIONAL -- Rel-10 or later  @sic R5-134957 sic@
}

--**************************************************************
--
-- PrimarySCHInfo
--
--**************************************************************

PrimarySCHInfo ::= SEQUENCE {
  tstdIndicator BOOLEAN,
  dl-TxPower DL-TxPower
}

--**************************************************************
--
-- RBInfo
--
--**************************************************************

RBInfo ::= SEQUENCE {
  sS-rlc-Info SS-RLC-Info OPTIONAL,
  sS-rlc-Info-r8 SS-RLC-Info-r8OrLater OPTIONAL,
  rB-LogCH-Mapping RB-LogCH-Mapping,
  relAspTypeExtension SEQUENCE{} OPTIONAL  -- @sic R5-130613 R5-134957 sic@
}

--**************************************************************
--
-- RBInfo-TDD
--
--**************************************************************

RBInfo-TDD ::= SEQUENCE {
  sS-rlc-Info SS-RLC-Info-TDD OPTIONAL,
  sS-rlc-Info-r8 SS-RLC-Info-r8OrLater-TDD OPTIONAL,
  rB-LogCH-Mapping RB-LogCH-Mapping,
  relAspTypeExtension SEQUENCE {} OPTIONAL -- Rel-10 or later @sic R5-134957 R5w130320 sic@
}

--**************************************************************
--
-- RB-ConfigType
--
--**************************************************************

RB-ConfigType ::= ENUMERATED {
  cell-NotConfigured (0),
  -- Configurations on DPCH
  cell-DCH-StandAloneSRB-NoConn (1),
  cell-NoDPCH (2),
  cell-DCH-StandAloneSRB (3),
  cell-DCH-Speech (4),
  cell-DCH-64kPS-RAB-SRB (7),
  cell-DCH-2AM-PS (17),
  -- Configurations on FACH
  cell-FACH-NoConn (18),
  cell-FACH (19),
  cell-FACH-NoDedicated (20),
  cell-FACH-PS (21),
  cell-Four-DTCH-PS-CS (44) ,
  cell-DCH-HS-DSCH(63),
  cell-FACH-HS(64),
  cell-DCH-64kPS-RAB-SRB-HS(65),
  -- E-DCH configurations
  cell-DCH-E-HS (84),
  cell-DCH-dlSRB-E-HS (85),
  cell-E-HS (86),
  cell-E-HS-MAC-TM-RAB (92),
  cell-E-HS-StandAloneSRB (98),
  cell-DCH-64kPS-AM-RAB (101),
  cell-SecondaryDualCell-SRB (118),
  cell-SecondaryDualCell-RAB (119),
  cell-FACH-UL-SRB (120), --@sic R5-150125 feFACH sic@
  cell-FACH-UL-SRB-NoConn (121), --@sic R5-150125 feFACH sic@
  cell-FACH-UL-PS (122),	--@sic R5-150125 feFACH sic@
  cell-SecondaryDualCell-NoConn (123),
  cell-DCH-3AM-PS (131), --@sic R5s150283 sic@
  cell-FACH-UL-NoDedicated (138), --@sic R5-150125 feFACH sic@
  cell-FACH-UL-FallBack  (140), --@sic R5-150125 feFACH sic@
  cell-DCH-E-HS-TM-RAB (141) --@sic R5-150124 MultiFlow sic@
}

--**************************************************************
--
-- RB-LogCH-Mapping
--   Provide mapping information between RB, logical channel and CN domain.
--   When the logical channel is MTCH, the logicalChannelIdentity shall be consistent with MBMS-LogicalChIdentity in MBMS-PTM-RBInformation-N and MBMS-PTM-RBInformation-C being sent to the UE.
--   In rel-11 Multiflow inter-NodeB configuration RB is mapped to logical channel on two MAC-ehs entities.
--**************************************************************

RB-LogCH-Mapping ::= SEQUENCE {
  uLlogicalChannelIdentity LogicalChannelIdentity OPTIONAL,
  dLlogicalChannelIdentity LogicalChannelIdentity OPTIONAL,
  logicalChannelType LogicalChannelType OPTIONAL,
  cn-DomainIdentity CN-DomainIdentity OPTIONAL
}

--**************************************************************
--
-- RLC-IncMode
--
--**************************************************************

RLC-IncMode ::= ENUMERATED {notInc(0), inc(1)}

--**************************************************************
--
-- RL-Information-FDD
--   The range for powerOffsetOfTPC-PO2 and powerOffsetOfTFCI-PO1 and powerOffsetOfPILOT-PO3 is 0 dB to 6 dB, 0,25 dB per step.
--   The IE cfnTgtSfnFrameOffset is applied when adding another RL or moving the UE to another cell in DCH state in the timing-maintained hard handover or in the softhandover. The cfnTgtSfnFrameOffset is defined as being the time difference between the CFN and the SFN of the cell in which the RL is to be added.
--   The use of cfnTgtSfnFrameOffset and DOFF (Default DPCH Offset Value) is mutually exclusive. The IE cfnTgtSfnFrameOffset is omitted when configuring the 1st RL, or configuring the RL in the timing re-initialised hard handover where the required synchronisation information is provided in defaultDPCH-offsetValue in DL-CommonInformation.
--   In addition, TmTgt value is provided to dpch-FrameOffset in DL-DPCH-InfoPerRL-r5 or DL-DPCH-InfoPerRL-r6 as CFNchipOffset-Tgt. TmTgt can be observed by the UE, or calculated by the TTCN. If it is calculated,
--   TmTgt = (DOFF*512 + 38400 + TCell-Ref - TCell-Tgt) Mod 38400
--
--**************************************************************

RL-Information-FDD ::= SEQUENCE {
  powerOffsetOfTFCI-PO1 INTEGER (0..24),
  powerOffsetOfTPC-PO2 INTEGER (0..24),
  powerOffsetOfPILOT-PO3 INTEGER (0..24), --OPTIONAL, @sic R5-112477r1, FDD-TDD allignment sic@
  dl-TxPower DL-TxPower,
  dl-TxPowerMax DL-TxPower,
  dl-TxPowerMin DL-TxPower,
  cfnTgtSfnFrameOffset CfnTgtSfnFrameOffset OPTIONAL,
  dl-FDPCH-ShoConfig BOOLEAN DEFAULT FALSE -- Rel6 or later
}

--**************************************************************
--
-- RL-Information-TDD
--   The range for powerOffsetOfTPC-PO2 and powerOffsetOfTFCI-PO1 and powerOffsetOfPILOT-PO3 is 0 dB to 6 dB, 0,25 dB per step.
--   The IE cfnTgtSfnFrameOffset is applied when adding another RL or moving the UE to another cell in DCH state in the timing-maintained hard handover or in the softhandover. The cfnTgtSfnFrameOffset is defined as being the time difference between the CFN and the SFN of the cell in which the RL is to be added.
--   The use of cfnTgtSfnFrameOffset and DOFF (Default DPCH Offset Value) is mutually exclusive. The IE cfnTgtSfnFrameOffset is omitted when configuring the 1st RL, or configuring the RL in the timing re-initialised hard handover where the required synchronisation information is provided in defaultDPCH-offsetValue in DL-CommonInformation.
--   In addition, TmTgt value is provided to dpch-FrameOffset in DL-DPCH-InfoPerRL-r5 or DL-DPCH-InfoPerRL-r6 as CFNchipOffset-Tgt. TmTgt can be observed by the UE, or calculated by the TTCN. If it is calculated,
--   TmTgt = (DOFF*512 + 38400 + TCell-Ref - TCell-Tgt) Mod 38400
--
--**************************************************************

RL-Information-TDD ::= SEQUENCE {
  powerOffsetOfTFCI-PO1 INTEGER (0..24),
  powerOffsetOfTPC-PO2 INTEGER (0..24),
  powerOffsetOfPILOT-PO3 INTEGER (0..24), --OPTIONAL, @sic R5-112477r1, FDD-TDD allignment sic@
  dl-TxPower DL-TxPower,
  dl-TxPowerMax DL-TxPower,
  dl-TxPowerMin DL-TxPower,
  cfnTgtSfnFrameOffset CfnTgtSfnFrameOffset OPTIONAL,
  dL-TimeslotISCPInfoLCR  TimeslotListWithISCP  OPTIONAL
}

--**************************************************************
--
-- RRC-Rel-Status
--
--**************************************************************

RRC-Rel-Status ::= ENUMERATED {
  cell-Dch(0),
  cell-Fach-Dcch(1),
  cell-Fach-Ccch(2)
}

--**************************************************************
--
-- RRC-SequenceNumber
--   4 bits long
--
--**************************************************************

RRC-SequenceNumber ::= INTEGER (0..15 )

--**************************************************************
--
-- RRC-ServTested
--
--**************************************************************

RRC-ServTested ::= ENUMERATED {
  speech (0),
  conversational-64k (1),
  streaming-57-6k (2),
  ps-Interactive (3),
  ps-Background (4),
  ps-Streaming (5),
  ps-SubscribedTrafficClass (6) -- @sic R5s110771 sic@

}

--**************************************************************
--
-- RatType
--   To select route between each channels
--
--**************************************************************

RatType ::= ENUMERATED {
  fdd(0),
  tdd128(1)  -- @sic R5-134957 sic@
}

--**************************************************************
--
-- RegOr-MO
--
--**************************************************************

RegOr-MO ::= ENUMERATED {
  est-Reg(0),
  est-MO(1),
  est-MT(2)
}

--**************************************************************
--
-- RoutingInfo
--
--**************************************************************

RoutingInfo ::= CHOICE {
  physicalChannelIdentity INTEGER (0..31),
  transportChannelIdentity TransportChannelIdentity,
  logicalChannelIdentity LogicalChannelIdentity,
  rB-Identity INTEGER (-31..32),
  cn-DomainIdentity CN-DomainIdentity
}

--**************************************************************
--
-- ServingAndSecondaryCellActivation-Type
--
--**************************************************************

ServingAndSecondaryCellActivation-Type ::= SEQUENCE {
   servingCellId   INTEGER(0..63),
   secondaryCellId   INTEGER(0..63),
   secondaryServing-HS-DSCH-Cell   ENUMERATED { deactivated (0), activated (1) }    DEFAULT deactivated
}

--**************************************************************
--
-- CmacConfigReq-r10OrLaterExtensionType
-- Applicable Rel-10 or later
-- servingSecondaryCells is provided in 4C configurations
--
--**************************************************************
CmacConfigReq-r10OrLaterExtensionType ::= CHOICE {
	rel10-AspExt SEQUENCE	{
		servingSecondaryCells  SEQUENCE {	-- 3C/4C HSDPA configuration
			servingCellId				INTEGER(0..63), 
			secondaryCellActivationList	SecondaryCellActivationList-Type
		} OPTIONAL
	}
}

--**************************************************************
--
-- SecondaryCellActivationList-Type
--
--**************************************************************
SecondaryCellActivationList-Type ::= SEQUENCE (SIZE (1..3)) OF SecondaryCellActivation-Type

--**************************************************************
--
-- SecondaryCellActivation-Type
--
--**************************************************************
SecondaryCellActivation-Type ::= SEQUENCE {
	secondaryCellId			INTEGER(0..63),
	secondaryServingStatus	ENUMERATED { deactivated (0), activated (1) } 
							DEFAULT deactivated
}

--**************************************************************
--
-- SCCPCHSlotFormat
--   Reference to TS25.211
--
--**************************************************************

SCCPCHSlotFormat ::= INTEGER (0..17)

--**************************************************************
--
-- SIB
--   Union of all system information blocks
--
--**************************************************************

SIB ::= CHOICE {
  sIB1 SysInfoType1,
  sIB2 SysInfoType2,
  sIB3 SysInfoType3,
  sIB4 SysInfoType4,
  sIB5 SysInfoType5,
  sIB6 SysInfoType6,
  sIB7 SysInfoType7,
  sIB8 SysInfoType8,
  sIB9 SysInfoType9,
  sIB10 SysInfoType10,
  sIB11 SysInfoType11,
  sIB12 SysInfoType12,
  sIB13 SysInfoType13,
  sIB13-1 SysInfoType13-1,
  sIB13-2 SysInfoType13-2,
  sIB13-3 SysInfoType13-3,
  sIB13-4 SysInfoType13-4,
  sIB14 SysInfoType14,
  sIB15 SysInfoType15,
  sIB15-1 SysInfoType15-1,
  sIB15-2 SysInfoType15-2,
  sIB15-3 SysInfoType15-3,
  sIB16 SysInfoType16,
  sIB17 SysInfoType17,
  sIB18 SysInfoType18,
  mIB MasterInformationBlock,
  sB1 SysInfoTypeSB1,
  sB2 SysInfoTypeSB2,
  sIB11bis SysInfoType11bis
}

--**************************************************************
--
-- SS-ActivationTime
--
--**************************************************************

SS-ActivationTime ::= CHOICE {
  activationCFN ActivationTime,
  activateNow NULL
}

--**************************************************************
--
-- SS-AddOrReconfMAC-dFlow
--   Applicable Rel-5 or later.
--
--**************************************************************

SS-AddOrReconfMAC-dFlow ::= SEQUENCE {
  mac-hs-AddReconfQueue-List SEQUENCE (SIZE(1..maxQueueIDs)) OF    SEQUENCE {
    mac-hs-AddReconfQueue SS-MAC-hs-AddReconfQueue } OPTIONAL,
  mac-hs-DelQueue-List SEQUENCE (SIZE(1..maxQueueIDs)) OF SEQUENCE {
    mac-hsQueueId INTEGER(0..7)
  } OPTIONAL
}

--**************************************************************
--
-- SS-Common-MAC-ehs-ReorderingQueue
--
--**************************************************************

SS-Common-MAC-ehs-ReorderingQueue ::= SEQUENCE
{
  common-MAC-ehs-ReorderingQueue Common-MAC-ehs-ReorderingQueue,
  priority INTEGER (0..7)
}

--**************************************************************
--
-- SS-Common-MAC-ehs-ReorderingQueueList
--
--**************************************************************

SS-Common-MAC-ehs-ReorderingQueueList ::= SEQUENCE (SIZE(1..maxQueueIDs)) OF SS-Common-MAC-ehs-ReorderingQueue


--**************************************************************
--
-- SS-DL-LogicalChannelMapping
--   If the macHeaderManipulation field is 'NormalMacHeader', then data transmitted on this logical channel shall have an appropriate MAC header added before it is sent to lower layers for transmission.
--   If the macHeaderManipulation field is 'OmitMacHeader', then data transmitted on this logical channel shall not have any MAC header information added, even if the logical channel type and mapping indicates that there should be a MAC header present. This allows the entire MAC PDU to be specified in the TTCN, so individual fields in the MAC header can be modified.
--   When used for DTCH mapping to MAC-d flow, rlc-SizeList shall choose "configured" according to the configured mAChsAddReconfQueue valules.
--   When the logical channel is MTCH, the logicalChannelIdentity shall be consistent with MBMS-LogicalChIdentity in MBMS-PTM-RBInformation-N and MBMS-PTM-RBInformation-C.
--
--**************************************************************

SS-DL-LogicalChannelMapping ::= SEQUENCE {
  macHeaderManipulation MAC-HeaderManipulation,
  dl-TransportChannelType SS-DL-TransportChannelType,
  logicalChannelIdentity LogicalChannelIdentity,
  logicalChannelType LogicalChannelType ,
  rlc-SizeList CHOICE {
    allSizes NULL,
    configured NULL,
    explicitList RLC-SizeExplicitList
  },
  mac-LogicalChannelPriority MAC-LogicalChannelPriority OPTIONAL
}

--**************************************************************
--
-- SS-DL-RLC-Mode
--   "dl-UM-outOfSeqDelivery" is present only for the DL-RLC entity connected to MCCH, and in the configuration with dl-UM-outOfSeqDelivery present the UM RLC can transmit RLC PDU containing SDU of ACCESS INFORMATION message out of sequence when it is necessary
--
--**************************************************************

SS-DL-RLC-Mode ::= SEQUENCE {
  dl-PayloadSize PayloadSize OPTIONAL,
  dl-RLCModeInfo UL-RLC-Mode,
  dl-UM-RLC-LI-size DL-UM-RLC-LI-size OPTIONAL, -- only for UM RLC configuration
  dl-UM-outOfSeqDelivery UM-RLC-OutOSeqDelivery-Info-r6 OPTIONAL, 
  dl-RLC-PDU-size CHOICE {
    fixedSize OctetModeRLC-SizeInfoType1,
    flexibleSize SS-FlexibleSize
  } OPTIONAL
}

--**************************************************************
--
-- SS-FlexibleSize
--
--**************************************************************
SS-FlexibleSize ::= SEQUENCE {
  li-Size ENUMERATED { size7 (0), size15 (1)}, -- Size of length indicator
  max-RLC-DataField-Size INTEGER (1..1503) OPTIONAL
  -- Maximum size of data field of RLC PDU (25.322, 9.2.2.9 and 25.433, 9.2.1.38c)
}

--**************************************************************
--
-- SS-DL-TransportChannelType
--
--**************************************************************

SS-DL-TransportChannelType ::= ENUMERATED {
  dch(0),
  fach(1),
  bch(2),
  pch(3),
  dsch(4),
  hsdsch(5) -- Rel-5 or later
}

--**************************************************************
--
-- SS-DRX-MAC-Info
--
--**************************************************************
SS-DRX-MAC-Info ::= SEQUENCE {
  mac-InactivityThreshold MAC-InactivityThreshold,
  mac-dtx-Cycle-2ms MAC-DTX-Cycle-2ms OPTIONAL,
  mac-dtx-Cycle-10ms MAC-DTX-Cycle-10ms OPTIONAL,
  timingInfo NewTiming
}


--**************************************************************
--
-- SS-E-AGCH-Info-FDD
--   Rel-6 or later.
--
--**************************************************************

SS-E-AGCH-Info-FDD ::= CHOICE {
 r6 SEQUENCE {
  e-AGCHInfo E-AGCH-Information,
  tti E-DCH-TTI,
  e-AGCH-PowerOffset INTEGER (0..255),
  -- Range and Step are acc to 25.433, 9.2.2.13Id @sic R5-153075 sic@
  -- Offset relative to P-CPICH
  e-RNTI-Primary E-RNTI OPTIONAL,
  e-RNTI-Secondary E-RNTI OPTIONAL,
  ss-DTX-Info DRX-Info OPTIONAL,
  sttdIndicator  BOOLEAN DEFAULT FALSE  -- @sic R5-120613 sic@
 },
 r8 SEQUENCE {
  e-AGCHInfo E-AGCH-Information-r8,
  tti E-DCH-TTI,
  e-AGCH-PowerOffset INTEGER (0..255),
  -- Range and Step are acc to 25.433, 9.2.2.13Id @sic R5-153075 sic@
  -- Offset relative to P-CPICH
  e-RNTI-Primary E-RNTI OPTIONAL,
  e-RNTI-Secondary E-RNTI OPTIONAL,
  ss-DTX-Info DRX-Info OPTIONAL,
  initialServingGrantValue	INTEGER (0..37)	OPTIONAL,
  sttdIndicator  BOOLEAN DEFAULT FALSE  -- @sic R5-120613 sic@ 
 },
 relAspTypeExtension SEQUENCE{}	-- Rel-10 or later @sic R5-130613 sic@
}

--**************************************************************
--
-- SS-E-AGCH-Info-TDD
--   Rel-7 or later.SS-E-AGCH-Info in TTCN-2
--
--**************************************************************

SS-E-AGCH-Info-TDD ::= CHOICE {
 r7 SEQUENCE {
  e-AGCH-ID-TDD     INTEGER (0..255),
  e-AGCHInfo         E-AGCH-Information-r7,  
  e-AGCH-PowerOffset     INTEGER (0..255),
  -- Range and Step are acc to 25.433, 9.2.2.13Id @sic R5-153141 sic@
  -- Offset relative to P-CPICH
  maximum-E-AGCH-Power     INTEGER (-350..150),
  carrier-Frequency     UARFCN OPTIONAL,
  e-RNTI     E-RNTI OPTIONAL, -- @sic R5w140013 sic@
  ss-DTX-Info DRX-Info OPTIONAL
  },
 r8 SEQUENCE {
  e-AGCH-ID-TDD     INTEGER (0..255),
  e-AGCHInfo         E-AGCH-Information-r8,  
  e-AGCH-PowerOffset     INTEGER (0..255),
  -- Range and Step are acc to 25.433, 9.2.2.13Id @sic R5-153141 sic@
  -- Offset relative to P-CPICH
  maximum-E-AGCH-Power     INTEGER (-350..150),
  carrier-Frequency     UARFCN OPTIONAL,
  e-RNTI            E-RNTI OPTIONAL,
  ss-E-AGCH-DRX-Info E-AGCH-DRX-Info-TDD128 OPTIONAL --@sic R5w140013 sic@
 },
 relAspTypeExtension SEQUENCE{} -- Rel-10 or later   @sic R5-134957 sic@
}

--**************************************************************
--
-- SS-E-DPCH-Info
--   Rel-6 or later.
--   If there is an UL-DPCH configured in the cell the E-DPCH shall use the same scramblingCodeType and scramblingCode as the UL-DPCH
--
--**************************************************************

SS-E-DPCH-Info-r6OrLater ::= CHOICE {
 r6 SEQUENCE {
  e-DPCCH-Info E-DPCCH-Info,
  e-DPDCH-Info E-DPDCH-Info,
  scramblingCodeType ScramblingCodeType OPTIONAL,
  scramblingCode UL-ScramblingCode OPTIONAL,
  tti E-DCH-TTI OPTIONAL,
  edch-PhysicalLayerCategory INTEGER (1..16)
 },
 r7 SEQUENCE {
  e-DPCCH-Info E-DPCCH-Info-r7,
  e-DPDCH-Info E-DPDCH-Info-r7,
  scramblingCodeType ScramblingCodeType OPTIONAL,
  scramblingCode UL-ScramblingCode OPTIONAL,
  tti E-DCH-TTI OPTIONAL,
  edch-PhysicalLayerCategory INTEGER (1..16) OPTIONAL,
  edch-PhysicalLayerCategory-extension INTEGER (7) OPTIONAL,
  ul-16QAM-Settings UL-16QAM-Settings OPTIONAL
 },
 r8 SEQUENCE {
  e-DPCCH-Info E-DPCCH-Info-r7,
  e-DPDCH-Info E-DPDCH-Info-r8,
  scramblingCodeType ScramblingCodeType OPTIONAL,
  scramblingCode UL-ScramblingCode OPTIONAL,
  tti E-DCH-TTI OPTIONAL,
  edch-PhysicalLayerCategory INTEGER (1..16) OPTIONAL,
  edch-PhysicalLayerCategory-extension INTEGER (7) OPTIONAL,
  ul-16QAM-Settings UL-16QAM-Settings OPTIONAL,
  s-offset INTEGER (0..9) OPTIONAL -- Used for enhFACH UL
 },
 r9 SEQUENCE {  -- @sic R5s110175 sic@
  e-DPCCH-Info E-DPCCH-Info-r7,
  e-DPDCH-Info E-DPDCH-Info-r8,
  scramblingCodeType ScramblingCodeType OPTIONAL,
  scramblingCode UL-ScramblingCode OPTIONAL,
  tti E-DCH-TTI OPTIONAL,
  edch-PhysicalLayerCategory INTEGER (1..16) OPTIONAL,
  edch-PhysicalLayerCategory-extension INTEGER (7) OPTIONAL,
  edch-PhysicalLayerCategory-extension2 INTEGER (8..9) OPTIONAL,
  ul-16QAM-Settings UL-16QAM-Settings OPTIONAL,
  s-offset INTEGER (0..9) OPTIONAL -- Used for enhFACH UL
 }, 
 relAspTypeExtension SEQUENCE{}	-- Rel-10 or later @sic R5-130613 sic@
 }

--**************************************************************
--
-- SS-E-DCH-Info-r7
--   Rel-7 or later.   
-- TDD
--**************************************************************

SS-E-DCH-Info-r7 ::= SEQUENCE {
  e-RUCCH-Info     E-RUCCH-Info OPTIONAL,
  e-PUCH-Info     SS-E-PUCH-Info OPTIONAL
}

--**************************************************************
--
-- SS-E-PUCH-Info
--   Rel-7 or later.   
-- TDD
--**************************************************************

SS-E-PUCH-Info ::= SEQUENCE {
  lTGI-Presence BOOLEAN,
  e-TFCS-Info E-TFCS-Info, 
  snpl-ReportType ENUMERATED {type1(0), type2(1)},
  prxBASEdes INTEGER (-112..-50 ), 
  beaconPLEst BOOLEAN OPTIONAL, 
  tpc-StepSize TPC-StepSizeTDD, 
  pebase-PowerControlGAP PowerControlGAP OPTIONAL, 
  ul-SynchronisationParameters UL-SynchronisationParameters-r4 OPTIONAL, 
  minimum-Allowed-Code-Rate INTEGER (0..63 ), 
  maximum-Allowed-Code-Rate INTEGER (0..63 ), 
  maximumNumOfRetransSchedInfo INTEGER (0..15 ), 
  retransTimerForSchedInfo ENUMERATED {ms10(0), ms15(1), ms20(2), ms25(3), ms30(4), ms35(5), ms40(6), ms45(7), ms50(8), ms55(9), ms60(10), ms65(11), ms70(12), ms75(13), ms80(14), ms85(15), ms90(16), ms95(17), ms100(18), ms110(19), ms120(20), ms140(21), ms160(22), ms200(23), ms240(24), ms280(25), ms320(26), ms400(27), ms480(28), ms560(29)},
  powerOffsetForSchedInfo INTEGER (0..6 ) OPTIONAL,
  e-DCH-phyLayCategory INTEGER (1..6 ) OPTIONAL,
  e-PUCH-TS-Information-per-UARFCN SEQUENCE (SIZE (1..maxTS-LCR-1)) OF SS-E-PUCH-Timeslot-Info,  
  carrier-Frequency UARFCN OPTIONAL
}

--**************************************************************
--
-- SS-E-PUCH-Timeslot-Info
--   Rel-7 or later TDD.
--
--**************************************************************
SS-E-PUCH-Timeslot-Info ::= SEQUENCE {
    timeslotNumber TimeslotNumber-LCR-r4, 
    midambleAllocationMode CHOICE
       {
        defaultMidamble NULL, 
        ueSpecificMidamble INTEGER (0..15 )
       }, 
    midambleConfiguration INTEGER (1..8 ), 
    channelisation-Code UL-TS-ChannelisationCode
 }

--**************************************************************
--
-- SS-E-HICH-Info
--   Rel-6 or later.
--
--**************************************************************

SS-E-HICH-Info ::= SEQUENCE {
  e-HICHInfo E-HICH-Information OPTIONAL, -- @sic R5s110175 sic@
  e-HICHInfoCommonEDCH E-HICH-Information-CommonEdch OPTIONAL, -- @sic R5s110175 sic@
  tti E-DCH-TTI,
  e-HICH-PowerOffset INTEGER (0..255),
  -- PowerOffset = -32 + offset * 0.25
  -- Unit dB, Range -32dB .. +31.75dB, Step +0.25dB
  -- (25.433, 9.2.2.13If), offset relative to P-CPICH @sic R5-153075 sic@
  sttdIndicator BOOLEAN DEFAULT FALSE,  -- @sic R5-120613 sic@
  relAspTypeExtension  SS-E-HICH-Info-r10OrLaterExtensionType	OPTIONAL  -- Rel-10 or later @sic R5-130613 R5-134957 sic@
}

--**************************************************************
--
-- SS-E-HICH-Info-TDD
--   Rel-7 or later. SS-E-HICH-Info in TTCN-2
--
--**************************************************************

SS-E-HICH-Info-TDD ::= SEQUENCE {
  n-E-HICH INTEGER (4..15 ), 
  maximum-E-HICH-Power INTEGER (-350..150),
  e-HICHInfoList SS-E-HICH-Info-List
}

--**************************************************************
--
-- SS-E-HICH-Info-List
--   Rel-7 or later. 
-- TDD
--**************************************************************

SS-E-HICH-Info-List ::= SEQUENCE (SIZE (1..maxNumE-HICH ) ) OF
  SS-E-HICH-Info-LCR

--**************************************************************
--
-- SS-E-HICH-Info-LCR
--   Rel-7 or later. 
-- TDD
--**************************************************************

SS-E-HICH-Info-LCR ::= SEQUENCE {
  e-HICH-ID-TDD     INTEGER (0..255),
  e-HICH-Type         ENUMERATED {scheduled(0), non-scheduled(1)},
  e-HICHInfo         E-HICH-Information-LCR,  
  carrier-Frequency     UARFCN OPTIONAL,  
  e-HICH-PowerOffset     INTEGER (0..255)
  -- PowerOffset = -32 + offset * 0.25
  -- Unit dB, Range -32dB .. +31.75dB, Step +0.25dB
  -- (25.433, 9.2.2.13If), offset relative to P-CPICH @sic R5-153141 sic@
}

--**************************************************************
--
-- SS-E-HICH-Info-r10OrLaterExtensionType
-- Rel-11 or later.
-- Only one of e-HICHInfo, e-HICHInfoCommonEDCH or e-HICHInfo-r11 can be present
--**************************************************************
SS-E-HICH-Info-r10OrLaterExtensionType ::= CHOICE {
	rel11-AspExt SEQUENCE	{
		e-HICHInfo-r11				E-HICH-Information-r11 	OPTIONAL
	}
}


--**************************************************************
--
-- SS-E-RGCH-Info
--   Rel-6 or later.
--   Presence of ss-DTX-Info indicates DL-DRX is enabled and SS shall transmit any requested RGCH only in occasions when UE is going to listen.
--   Only one of e-RGCHInfo and e-RGCHInfoCommonEDCH can be present
--**************************************************************

SS-E-RGCH-Info ::= SEQUENCE {
  e-RGCHInfo E-RGCH-Information OPTIONAL, -- @sic R5s110175 sic@
  e-RGCHInfoCommonEDCH E-RGCH-Information-CommonEdch OPTIONAL, -- @sic R5s110175 sic@
  tti E-DCH-TTI ,
  e-RGCH-PowerOffset INTEGER (0..255),
     -- Range Range:-32 .. +31.75 dB, Step: 0.25 dB
     -- Offset relative to P-CPICH
  ss-DTX-Info DRX-Info OPTIONAL,
  sttdIndicator BOOLEAN DEFAULT FALSE,  -- @sic R5-120613 sic@
  relAspTypeExtension SEQUENCE{} OPTIONAL	-- Rel-10 or later @sic R5-130613 sic@
}

--**************************************************************
--
-- SS-IntegrityProtActivationTimeInfo
--   Omitting rrc-MessageSequenceNumber means activation time set to "now".
--
--**************************************************************

SS-IntegrityProtActivationTimeInfo ::= SEQUENCE
{
  rb-Identity INTEGER (-31..32),
  rrc-MessageSequenceNumber RRC-MessageSequenceNumber OPTIONAL
}

--**************************************************************
--
-- SS-MAC-ehs-AddReconfReordQ
--
--**************************************************************

SS-MAC-ehs-AddReconfReordQ ::= SEQUENCE
{
  mAC-ehs-AddReconfReordQ MAC-ehs-AddReconfReordQ,
  priority INTEGER (0..7)
}

--**************************************************************
--
-- SS-MAC-ehs-AddReconfReordQ-r9
--
--**************************************************************

SS-MAC-ehs-AddReconfReordQ-r9 ::= SEQUENCE
{
  mAC-ehs-AddReconfReordQ MAC-ehs-AddReconfReordQ-r9,
  priority INTEGER (0..7)
}

--**************************************************************
--
-- SS-MAC-ehs-AddReconfReordQ-r11
-- Applicable Rel-11or later
-- The priority of PriorityQueue shall set according to the priority of logical channels which is mapped on to this priority queue.
-- NOTE:	The range of priority of PriorityQueue is from 0 to 7 and 0 is the lowest priority.
--**************************************************************
SS-MAC-ehs-AddReconfReordQ-r11 ::= SEQUENCE	{
	mAC-ehs-AddReconfReordQ		MAC-ehs-AddReconfReordQ-r11,
	priority					INTEGER(0..7)
}


--**************************************************************
--
-- SS-MAC-ehs-AddReconfReordQueueList
--
--**************************************************************

SS-MAC-ehs-AddReconfReordQueueList ::= SEQUENCE (SIZE (1..maxQueueIDs)) OF SS-MAC-ehs-AddReconfReordQ

--**************************************************************
--
-- SS-MAC-ehs-AddReconfReordQueueList-r9
--
--**************************************************************

SS-MAC-ehs-AddReconfReordQueueList-r9 ::= SEQUENCE (SIZE (1..maxQueueIDs)) OF SS-MAC-ehs-AddReconfReordQ-r9

--**************************************************************
--
-- SS-MAC-ehs-AddReconfReordQueueList-r11
-- Applicable Rel-11 or later 
--**************************************************************

SS-MAC-ehs-AddReconfReordQueueList-r11 ::= SEQUENCE (SIZE (1..maxQueueIDs)) OF SS-MAC-ehs-AddReconfReordQ-r11

--**************************************************************
--
-- SS-MAC-hs-AddReconfQueue
--   Applicable Rel-5 or later.
--   When writing TTCN constraints the TTCN writer shall set the priority of PriorityQueue in this object correctly acoording to the priority of logical channels which is mapped on to this priority queue.
--   And please note that : the range of priority of PriorityQueue is from 0 to 7 and 0 is the lowest priority.
--
--**************************************************************

SS-MAC-hs-AddReconfQueue ::= SEQUENCE {
  mAChsAddReconfQueue MAC-hs-AddReconfQueue,
  logicalChannelList SEQUENCE OF LogicalChannelIdentity,
  -- logical channels mapping onto the priority queue
  -- which is specified in maChsAddReconfQueue
  priority INTEGER(0..7),
  discardTimer ENUMERATED { v20(0),v40(1),v60(2),v80(3),v100(4),
    v120(5),v140(6),v160(7),v180(8),v200(9),
    v250(10),v300(11),v400(12),v500(13),
    v750(14),v1000(15),v1250(16),v1500(17),
    v1750(18),v2000(19),v2500(20),v3000(21),
    v3500(22),v4000(23),v4500(24),v5000(25),
    v7500(26)
  } OPTIONAL
}

--**************************************************************
--
-- SS-RLC-Info
--   UL and DL have been swapped intentionally in this type definition. This is to maximize re-use of the type definitions in 3GPP TS 25.331 which are intended to configure a UE, where UL is transmission, and DL is reception. For the SS, UL is reception, and DL is transmission.
--   For example, consider configuring a DL AM RLC entity (transmitter) in the SS. The transmission parameters to be configured include PollingInformation, Transmission-RLC-Discard etc. If the DL-AM-RLC-Mode type definition is used to configure this entity, it is only possible to configure reception parameters such as StatusInformation, and receiving window size.
--   By swapping UL and DL, it is possible to configure the DL AM RLC entity using the existing type definition UL-AM-RLC-Info, which contains all of the required transmission parameters.
--
--**************************************************************

SS-RLC-Info ::= SEQUENCE {
  sS-ul-RLC-Mode DL-RLC-Mode OPTIONAL,
  sS-dl-RLC-Mode SS-DL-RLC-Mode OPTIONAL,
  rlc-OneSidedReEst BOOLEAN DEFAULT FALSE, 
  altE-bitInterpretation ENUMERATED {false (0), true (1)} DEFAULT false,
  useSpecialValueOfHEField ENUMERATED {false (0), true (1)} DEFAULT false,
  uM-SN-DeliveryMode ENUMERATED { nonConfigured(0), configured(1)} DEFAULT nonConfigured
}

--**************************************************************
--
-- SS-RLC-Info-TDD
--   UL and DL have been swapped intentionally in this type definition. This is to maximize re-use of the type definitions in 3GPP TS 25.331 which are intended to configure a UE, where UL is transmission, and DL is reception. For the SS, UL is reception, and DL is transmission.
--   For example, consider configuring a DL AM RLC entity (transmitter) in the SS. The transmission parameters to be configured include PollingInformation, Transmission-RLC-Discard etc. If the DL-AM-RLC-Mode type definition is used to configure this entity, it is only possible to configure reception parameters such as StatusInformation, and receiving window size.
--   By swapping UL and DL, it is possible to configure the DL AM RLC entity using the existing type definition UL-AM-RLC-Info, which contains all of the required transmission parameters.
--
--**************************************************************

SS-RLC-Info-TDD ::= SEQUENCE {
  sS-ul-RLC-Mode DL-RLC-Mode OPTIONAL,
  sS-ul-PayloadSize PayloadSize OPTIONAL,
  sS-dl-RLC-Mode SS-DL-RLC-Mode OPTIONAL,
  rlc-OneSidedReEst BOOLEAN DEFAULT FALSE, 
  altE-bitInterpretation ENUMERATED {false (0), true (1)} DEFAULT false,
  useSpecialValueOfHEField ENUMERATED {false (0), true (1)} DEFAULT false,
  uM-SN-DeliveryMode ENUMERATED { nonConfigured(0), configured(1)} DEFAULT nonConfigured

}

--**************************************************************
--
-- SS-RLC-Info-r8OrLater
--   Applicable for r8OrLater
--   UL and DL have been swapped intentionally in this type definition. This is to maximize re-use of the type definitions in 3GPP TS 25.331 which are intended to configure a UE, where UL is transmission, and DL is reception. For the SS, UL is reception, and DL is transmission.
--   For example, consider configuring a DL AM RLC entity (transmitter) in the SS. The transmission parameters to be configured include PollingInformation, Transmission-RLC-Discard etc. If the DL-AM-RLC-Mode type definition is used to configure this entity, it is only possible to configure reception parameters such as StatusInformation, and receiving window size.
--   By swapping UL and DL, it is possible to configure the DL AM RLC entity using the existing type definition UL-AM-RLC-Info, which contains all of the required transmission parameters.
--
--**************************************************************

SS-RLC-Info-r8OrLater ::= CHOICE {
r8 SEQUENCE {
    sS-ul-RLC-Mode DL-RLC-Mode-r7 OPTIONAL,
    sS-dl-RLC-Mode SS-DL-RLC-Mode OPTIONAL,
    rlc-OneSidedReEst BOOLEAN DEFAULT FALSE, 
    altE-bitInterpretation ENUMERATED {false (0), true (1)} DEFAULT false,
    useSpecialValueOfHEField ENUMERATED {false (0), true (1)} DEFAULT false,
    uM-SN-DeliveryMode ENUMERATED { nonConfigured(0), configured(1)} DEFAULT nonConfigured
},
relAspTypeExtension SS-RLC-Info-r10OrLaterExtensionType 	-- Rel-10 or later  @sic R5-130613 R5-134957 sic@
}

--**************************************************************
--
-- SS-RLC-Info-r8OrLater-TDD
--   Applicable for r8OrLater
--   UL and DL have been swapped intentionally in this type definition. This is to maximize re-use of the type definitions in 3GPP TS 25.331 which are intended to configure a UE, where UL is transmission, and DL is reception. For the SS, UL is reception, and DL is transmission.
--   For example, consider configuring a DL AM RLC entity (transmitter) in the SS. The transmission parameters to be configured include PollingInformation, Transmission-RLC-Discard etc. If the DL-AM-RLC-Mode type definition is used to configure this entity, it is only possible to configure reception parameters such as StatusInformation, and receiving window size.
--   By swapping UL and DL, it is possible to configure the DL AM RLC entity using the existing type definition UL-AM-RLC-Info, which contains all of the required transmission parameters.
--
--**************************************************************

SS-RLC-Info-r8OrLater-TDD ::= CHOICE {
r8 SEQUENCE {
    sS-ul-RLC-Mode DL-RLC-Mode-r7 OPTIONAL,
    sS-ul-PayloadSize PayloadSize OPTIONAL,
    sS-dl-RLC-Mode SS-DL-RLC-Mode OPTIONAL,
    rlc-OneSidedReEst BOOLEAN DEFAULT FALSE, 
    altE-bitInterpretation ENUMERATED {false (0), true (1)} DEFAULT false,
    useSpecialValueOfHEField ENUMERATED {false (0), true (1)} DEFAULT false,
    uM-SN-DeliveryMode ENUMERATED { nonConfigured(0), configured(1)} DEFAULT nonConfigured
},
relAspTypeExtension		SS-RLC-Info-r10OrLaterExtensionType -- Rel-10 or later @sic R5-134957 sic@
}

--**************************************************************
--
-- SS-RLC-Info-r10OrLaterExtensionType
-- Rel-11 or later 
--**************************************************************
SS-RLC-Info-r10OrLaterExtensionType ::= CHOICE {
	rel11-AspExt SEQUENCE	{  -- Rel-11 or later
		sS-ul-RLC-Mode			DL-RLC-Mode-r11		OPTIONAL,
		sS-dl-RLC-Mode			SS-DL-RLC-Mode		OPTIONAL,
		rlc-OneSidedReEst		BOOLEAN				DEFAULT FALSE,
		altE-bitInterpretation	ENUMERATED {false (0), true (1)} DEFAULT false,
			-- applicable only for UM RLC mode
		useSpecialValueOfHEField ENUMERATED {false (0), true (1)} DEFAULT false,
			-- applicable only for AM RLC mode
		uM-SN-DeliveryMode	ENUMERATED { nonConfigured(0), configured(1)} 
							DEFAULT nonConfigured
	}
}

--**************************************************************
--
-- SS-UL-DPCCH-DRX-Info
--
--**************************************************************
SS-UL-DPCCH-DRX-Info ::= SEQUENCE {
  ss-DRX-Info DTX-Info OPTIONAL,

  dtx-DRX-timingInfo DTX-DRX-TimingInfo-r7 OPTIONAL,

  uplink-DPCCHSlotFormatInformation Uplink-DPCCH-Slot-Format-Information
}

--**************************************************************
--
-- SS-UL-LogicalChannelMapping
--   If the macHeaderManipulation field is 'normalMacHeader', then data received on the transport channel supporting this logical channel shall have it's MAC header inspected to determine the appropriate routing, and removed as normal. The MAC SDU shall be passed to the appropriate logical channel.
--   If the macHeaderManipulation field field is 'OmitMacHeader', then data received on the transport channel supporting this logical channel shall have it's MAC header inspected to determine the appropriate routing, but the MAC layer shall not remove the MAC header. Thus the entire MAC PDU shall be passed to the appropriate logical channel, and the MAC header can be checked by the TTCN.
--
--**************************************************************

SS-UL-LogicalChannelMapping ::= SEQUENCE {
  macHeaderManipulation MAC-HeaderManipulation,
  ul-TransportChannelType SS-UL-TransportChannelType,
  logicalChannelIdentity LogicalChannelIdentity,
  logicalChannelType LogicalChannelType
}

--**************************************************************
--
-- SS-UL-LogicalChannelMapping-TDD
--   If the macHeaderManipulation field is 'normalMacHeader', then data received on the transport channel supporting this logical channel shall have it's MAC header inspected to determine the appropriate routing, and removed as normal. The MAC SDU shall be passed to the appropriate logical channel.
--   If the macHeaderManipulation field field is 'OmitMacHeader', then data received on the transport channel supporting this logical channel shall have it's MAC header inspected to determine the appropriate routing, but the MAC layer shall not remove the MAC header. Thus the entire MAC PDU shall be passed to the appropriate logical channel, and the MAC header can be checked by the TTCN.
--   @sic R5-134957 R5w130320: TDD TTCN-2/3 differences sic@
--
--**************************************************************

SS-UL-LogicalChannelMapping-TDD ::= SEQUENCE {
  macHeaderManipulation MAC-HeaderManipulation,
  ul-TransportChannelType SS-UL-TransportChannelType-TDD,  --@sic R5-134957 R5w130320: TDD TTCN-2/3 differences sic@
  logicalChannelIdentity LogicalChannelIdentity,
  logicalChannelType LogicalChannelType
}

--**************************************************************
--
-- SS-UL-TransportChannelType
--
--**************************************************************

SS-UL-TransportChannelType ::= ENUMERATED {
  dch(0),
  rach(1),
  cpch(2),
  usch(3),
  edch (4) -- Rel-6 or later
}

--**************************************************************
--
-- SS-UL-TransportChannelType-TDD
--  @sic R5-134957 R5w130320: TDD TTCN-2/3 differences sic@
--
--**************************************************************
SS-UL-TransportChannelType-TDD ::= ENUMERATED {
  dch(0),
  rach(1),
  usch(2),
  edch (3) -- Rel-6 or later
}


--**************************************************************
--
-- SecondaryCCPCHInfo-FDD
--   The range for powerOffsetOfTFCI-PO1 and powerOffsetOfPILOT-PO3 is 0 dB to 6 dB, 0.25 dB per step.
--   mbms-softCombTimingOffset is present when L1-combination applies
--   When configuring SCCPCH for MBMS "positionFixedOrFlexible" shall be set to Flexible, and sCCPCHSlotFormat shall be chosen to the one without pilot bits
--
--**************************************************************

SecondaryCCPCHInfo-FDD ::= SEQUENCE {
  scramblingCode INTEGER(0..15),
  dl-ChannelizationCode SF256-AndCodeNumber,
  sCCPCHSlotFormat SCCPCHSlotFormat,
  timingOffset INTEGER (0..149),
  positionFixedOrFlexible PositionFixedOrFlexible,
  sttd-Indicator BOOLEAN,
  dl-TxPower DL-TxPower,
  powerOffsetOfTFCI-PO1 INTEGER (0..24),
  powerOffsetOfPILOT-PO3 INTEGER (0..24),
  mbms-softCombTimingOffset MBMS-SoftComb-TimingOffset OPTIONAL --Rel-6 or later 
  -- timeSlot TimeSlot OPTIONAL,
  -- burstType BurstType OPTIONAL,
  -- midambleShift MidambleShift OPTIONAL,
  -- offset Offset OPTIONAL,
  -- repetitionPeriod RepetitionPeriod OPTIONAL,
  -- repetitionLength RepetitionLength OPTIONAL,
  -- tFCIPresence TFCIPresence OPTIONAL,
}

--**************************************************************
--
-- SecondaryCCPCHInfo-TDD
--   The range for powerOffsetOfTFCI-PO1 and powerOffsetOfPILOT-PO3 is 0 dB to 6 dB, 0.25 dB per step.
--   mbms-softCombTimingOffset is present when L1-combination applies
--   When configuring SCCPCH for MBMS "positionFixedOrFlexible" shall be set to Flexible, and sCCPCHSlotFormat shall be chosen to the one without pilot bits
--
--**************************************************************

SecondaryCCPCHInfo-TDD ::= SEQUENCE {
  tstd-Indicator ENUMERATED {notApplied(0),applied(1)},
  sctd-Indicator ENUMERATED {notApplied(0),applied(1)},
  dl-TxPower DL-TxPower,
  commonTimeSlotInfo CommonTimeslotInfoSCCPCH,
  channelisationCode SCCPCH-ChannelisationCodeList,
  individualTimeslotInfo IndividualTimeslotInfo-LCR-r4,
  powerOffsetOfTFCI-PO1 INTEGER (0..24) OPTIONAL
}

--**************************************************************
--
-- SecondaryCPICHInfo
--
--**************************************************************

SecondaryCPICHInfo ::= SEQUENCE {
  scramblingCode INTEGER(0..63),
  dl-ChannelizationCode SF512-AndCodeNumber,
  dl-TxPower DL-TxPower,
  mimoAntenna MimoAntennaConfigType DEFAULT noMimo
}

--**************************************************************
--
-- SecondarySCHInfo
--
--**************************************************************

SecondarySCHInfo ::= SEQUENCE {
  tstdIndicator BOOLEAN,
  dl-TxPower DL-TxPower
}

--**************************************************************
--
-- SecurityInfo
--   The integrityKey is not applicable to MAC
--   Detailed comments:
--   When the SS receives SecuritiyInfo, the SS first stores the contents. The SecurityInfo contents is not activated ion of the contents follows until receiving the subsequent ASP, CRLC-Ciphering-Activate-REQ, CMAC-Ciphering-Activate-REQ or CRLC-Integrity-Activate-REQ. Omitted fields of SecurityInfo shall not be affected by the subsequent ASP at the activation time.EXAMPLE:    Omitting of startValue indicates not to re-initialize the relevant                 COUNT?C or COUNT-I, omitting of cipheringKey indicates that the                 current ciphering key  is valid..
--
--**************************************************************

SecurityInfo ::= SEQUENCE {
  cn-DomainIdentity CN-DomainIdentity,
  startValue START-Value OPTIONAL,
  cipheringKey BIT STRING (SIZE (128)) OPTIONAL,
  integrityKey BIT STRING (SIZE (128)) OPTIONAL,
  gsmCipheringKey BIT STRING (SIZE (64)) OPTIONAL
}

--**************************************************************
--
-- SegmentsOfSysInfoBlock
--   The structure holding the segments of a MIB/SIB/SB, maximum number of segments is 16.
--
--**************************************************************

SegmentsOfSysInfoBlock ::= SEQUENCE
{
  segCount INTEGER (1..16),
  seg1 BIT STRING (SIZE (1..226)),
  seg2 BIT STRING (SIZE (1..222)) OPTIONAL,
  seg3 BIT STRING (SIZE (1..222)) OPTIONAL,
  seg4 BIT STRING (SIZE (1..222)) OPTIONAL,
  seg5 BIT STRING (SIZE (1..222)) OPTIONAL,
  seg6 BIT STRING (SIZE (1..222)) OPTIONAL,
  seg7 BIT STRING (SIZE (1..222)) OPTIONAL,
  seg8 BIT STRING (SIZE (1..222)) OPTIONAL,
  seg9 BIT STRING (SIZE (1..222)) OPTIONAL,
  seg10 BIT STRING (SIZE (1..222)) OPTIONAL,
  seg11 BIT STRING (SIZE (1..222)) OPTIONAL,
  seg12 BIT STRING (SIZE (1..222)) OPTIONAL,
  seg13 BIT STRING (SIZE (1..222)) OPTIONAL,
  seg14 BIT STRING (SIZE (1..222)) OPTIONAL,
  seg15 BIT STRING (SIZE (1..222)) OPTIONAL,
  seg16 BIT STRING (SIZE (1..222)) OPTIONAL
}

--**************************************************************
--
-- SupportFlag
--   The default value noNeed indicates that the SS does not perform the operation mentioned in CRLC-ProhibitRLC-Ack-REQ, but performs the suspension / resume of  UL RLC PDU data.
--   If the non default values are taken, the SS has either prohibited, or continued acknowledging RLC SDUs.
--
--**************************************************************

SupportFlag ::= ENUMERATED {ackProhibited(0), ackContinued(1), noNeed (2)}

--**************************************************************
--
-- Tcell
--   Timing offset between reference channel and this channel ( unit : 256 chips )
--
--**************************************************************

Tcell ::= INTEGER (0..38399)

--**************************************************************
--
-- TrCHInfo
--   The same TFCS information should be provided to the PHY and MAC layers at all times. When a CMAC-Config-REQ is used to configure the MAC layer, a corresponding CPHY-TrCH-Config-REQ should be sent to the PHY layer to ensure that the configuration is consistent.
--   For MAC-hs configuration:
--   When ulconnectedTrCHList, ulTFCS, dlconnectedTrCHList and dlTFCS are omitted this ASP configures an MAC-hs entity.
--
--**************************************************************

TrCHInfo ::= SEQUENCE
{
  ulconnectedTrCHList SEQUENCE (SIZE (1..maxulTrCH)) OF SEQUENCE {
    trchid TransportChannelIdentity,
    transportChannelInfo CommonOrDedicatedTFS
  } OPTIONAL,
  ulTFCS TFCS OPTIONAL,
  dlconnectedTrCHList SEQUENCE (SIZE (1..maxdlTrCH)) OF SEQUENCE {
    trchid TransportChannelIdentity,
    transportChannelInfo CommonOrDedicatedTFS
  } OPTIONAL,
  dlTFCS TFCS OPTIONAL,
  hsDSCHMacdFlows HS-DSCHMACdFlows OPTIONAL, -- Rel-5 or later
  ehs-DSCH-Flows EHS-DSCH-Flows OPTIONAL, -- Rel-7 or later
  ehs-DSCH-CommonFlows EHS-DSCH-CommonFlows OPTIONAL, -- Rel-7 or later
  ehs-DSCH-Flows-r9 EHS-DSCH-Flows-r9 OPTIONAL, -- Rel-9 or later @sic R5s110175 sic@
  relAspTypeExtension  TrCHInfo-r10OrLaterExtensionType OPTIONAL	-- Rel-10 or later @sic R5-130613 R5-134957 sic@
}

--**************************************************************
--
-- TrCHInfo-TDD
--   The same TFCS information should be provided to the PHY and MAC layers at all times. When a CMAC-Config-REQ is used to configure the MAC layer, a corresponding CPHY-TrCH-Config-REQ should be sent to the PHY layer to ensure that the configuration is consistent.
--   For MAC-hs configuration:
--   When ulconnectedTrCHList, ulTFCS, dlconnectedTrCHList and dlTFCS are omitted this ASP configures an MAC-hs entity.
--
--**************************************************************

TrCHInfo-TDD ::= SEQUENCE
{
  ulconnectedTrCHList SEQUENCE (SIZE (1..maxulTrCH)) OF SEQUENCE {
    trchid TransportChannelIdentity,
    transportChannelInfo CommonOrDedicatedTFS-TDD
  } OPTIONAL,
  ulTFCS TFCS OPTIONAL,
  dlconnectedTrCHList SEQUENCE (SIZE (1..maxdlTrCH)) OF SEQUENCE {
    trchid TransportChannelIdentity,
    transportChannelInfo CommonOrDedicatedTFS-TDD
  } OPTIONAL,
  dlTFCS TFCS OPTIONAL,
  hsDSCHMacdFlows HS-DSCHMACdFlows-TDD OPTIONAL, -- Rel-5 or later
  ehs-DSCH-Flows EHS-DSCH-Flows OPTIONAL, -- Rel-7 or later
  ehs-DSCH-CommonFlows EHS-DSCH-CommonFlows OPTIONAL, -- Rel-7 or later
  ehs-DSCH-Flows-r9 EHS-DSCH-Flows-r9 OPTIONAL, -- Rel-9 or later
  relAspTypeExtension TrCHInfo-r10OrLaterExtensionType  OPTIONAL -- Rel-10 or later @sic R5-130613 R5s150329 sic@
}

--**************************************************************
--
-- TrCHInfo-r10OrLaterExtensionType
-- Rel-11 or later 
-- For Rel-11 MAC-ehs configuration:
-- When ulconnectedTrCHList, ulTFCS, dlconnectedTrCHList and dlTFCS are omitted and ehs-DSCH-Flows or E-HS-DSCH-Common Flows or ehs-DSCH-Flows-r11 is present this ASP configures an MAC-ehs  entity.
-- Only one of hsDSCHMacdFlows or ehs-DSCH-Flows or ehs-DSCH-Flows-r9 or  ehs-DSCH-Flows-r11 can be present.
-- For Rel-12, UL DCH configuration:
-- Only one of ulTFCS in TrCHInfo and ulTFCS-r12 can be present.
-- For Rel-13 MAC-hs or MAC-ehs configuration:
-- Only one of hsDSCHMacdFlows or ehs_DSCH_Flows or ehs_DSCH_Flows_r9 or ehs_DSCH_Flows_r11 or ehs_DSCH_Flows_r13 can be present.
-- @sic R5s150329 R5-176156 sic@
--**************************************************************
TrCHInfo-r10OrLaterExtensionType ::= CHOICE {
	rel11-AspExt SEQUENCE	{  -- Rel-11 or later
		ehs-DSCH-Flows-r11		EHS-DSCH-Flows-r11		OPTIONAL
	},
	rel12-AspExt SEQUENCE	{ -- Rel-12 or later
		ulTFCS-r12				TFCS-r12					OPTIONAL
	},
	rel13-AspExt SEQUENCE	{  -- Rel-13 or later
		ehs-DSCH-Flows-r13		EHS-DSCH-Flows-r13		OPTIONAL
	}
 }

--**************************************************************
--
-- TrCH-LogCHMappingList
--   maxLogCHperTrCH = 8
--
--**************************************************************

TrCH-LogCHMappingList ::= SEQUENCE (SIZE (1..maxLogCHperTrCH)) OF TrCH-LogicalChannelMapping

--**************************************************************
--
-- TrCH-LogCHMappingList-TDD
--  maxLogCHperTrCH = 8
--  @sic R5-134957: TDD TTCN-2/3 differences sic@
--
--**************************************************************

TrCH-LogCHMappingList-TDD ::= SEQUENCE (SIZE (1..maxLogCHperTrCH)) OF TrCH-LogicalChannelMapping-TDD

--**************************************************************
--
-- TrCH-LogCHMappingList1
--  maxulTrCH = maxdlTrCH = 16
--  dlconnectedMACdFlows is used for MAC-hs and dlconnectedMAC-ehsFlows for MAC-ehs configurations in dedicated. 
--  dlconnectedMAC-ehsCommonFlow is used for MAC-ehs in Common state. For BCCH and PCCH in common state, the mac-ehs-QueueId is omitted, no reordering is applied and the TSN and SI fields are always set to zero (according to 3GPP TS 25.321 [17], subclauses 9.1.4 and 11.6.4.4)
--  dlconnectedMAC-ehsFlowsDC is used when dual cell or 4C-HSDPA or Multiflow is activated.
--
--**************************************************************

TrCH-LogCHMappingList1 ::= SEQUENCE
{
  ulconnectedTrCHList SEQUENCE (SIZE (1..maxulTrCH)) OF SEQUENCE {
    trchid TransportChannelIdentity,
    trCH-LogCHMappingList TrCH-LogCHMappingList} OPTIONAL,
  dlconnectedTrCHList SEQUENCE (SIZE (1..maxdlTrCH)) OF SEQUENCE {
    trchid TransportChannelIdentity,
    trCH-LogCHMappingList TrCH-LogCHMappingList} OPTIONAL,
  dlconnectedMACdFlows SEQUENCE (SIZE (1..8)) OF SEQUENCE {
    mac-dFlowId MAC-d-FlowIdentity,
    trCH-LogCHMappingList TrCH-LogCHMappingList
  } OPTIONAL, -- Rel-5 or later
  dlconnectedMAC-ehsFlows SEQUENCE (SIZE (1..8)) OF SEQUENCE {
    mac-ehs-QueueId MAC-ehs-QueueId,
    trCH-LogCHMappingList TrCH-LogCHMappingList
  } OPTIONAL, -- Rel-7 or later
  dlconnectedMAC-ehsCommonFlows SEQUENCE (SIZE (1..8)) OF SEQUENCE {
    mac-ehs-QueueId MAC-ehs-QueueId OPTIONAL,
    trCH-LogCHMappingList TrCH-LogCHMappingList
  } OPTIONAL, -- Rel-7 or later
  dlconnectedMAC-ehsFlowsDC SEQUENCE (SIZE (1..8)) OF SEQUENCE {
    mac-ehs-QueueId MAC-ehs-QueueId, -- @sic R5-112477 sic@
    trCH-LogCHMappingList TrCH-LogCHMappingList
  } OPTIONAL, -- Rel-8 or later @sic R5-110104 sic@
  relAspTypeExtension SEQUENCE{}	OPTIONAL	-- Rel-10 or later @sic R5-130613 sic@
}

--**************************************************************
--
-- TrCH-LogCHMappingList1-TDD
--  maxulTrCH = maxdlTrCH = 16
--  dlconnectedMACdFlows is used for MAC-hs and dlconnectedMAC-ehsFlows for MAC-ehs configurations in dedicated. 
--  dlconnectedMAC-ehsCommonFlow is used for MAC-ehs in Common state. For BCCH and PCCH in common state, the mac-ehs-QueueId is omitted, no reordering is applied and the TSN and SI fields are always set to zero (according to 3GPP TS 25.321 [17], subclauses 9.1.4 and 11.6.4.4)
--  dlconnectedMAC-ehsFlowsDC is used when dual cell or 4C-HSDPA is activated.
--  @sic R5-134957: TDD TTCN-2/3 differences sic@
--
--**************************************************************
TrCH-LogCHMappingList1-TDD ::= SEQUENCE
{
  ulconnectedTrCHList SEQUENCE (SIZE (1..maxulTrCH)) OF SEQUENCE {
    trchid TransportChannelIdentity,
    trCH-LogCHMappingList TrCH-LogCHMappingList-TDD} OPTIONAL,
  dlconnectedTrCHList SEQUENCE (SIZE (1..maxdlTrCH)) OF SEQUENCE {
    trchid TransportChannelIdentity,
    trCH-LogCHMappingList TrCH-LogCHMappingList-TDD} OPTIONAL,
  dlconnectedMACdFlows SEQUENCE (SIZE (1..8)) OF SEQUENCE {
    mac-dFlowId MAC-d-FlowIdentity,
    trCH-LogCHMappingList TrCH-LogCHMappingList-TDD
  } OPTIONAL, -- Rel-5 or later
  dlconnectedMAC-ehsFlows SEQUENCE (SIZE (1..8)) OF SEQUENCE {
    mac-ehs-QueueId MAC-ehs-QueueId,
    trCH-LogCHMappingList TrCH-LogCHMappingList-TDD
  } OPTIONAL, -- Rel-7 or later
  dlconnectedMAC-ehsCommonFlows SEQUENCE (SIZE (1..8)) OF SEQUENCE {
    mac-ehs-QueueId MAC-ehs-QueueId OPTIONAL,
    trCH-LogCHMappingList TrCH-LogCHMappingList-TDD
  } OPTIONAL, -- Rel-7 or later
  dlconnectedMAC-ehsFlowsDC SEQUENCE (SIZE (1..8)) OF SEQUENCE {
    mac-ehs-QueueId MAC-ehs-QueueId, -- @sic R5-112477 sic@
    trCH-LogCHMappingList TrCH-LogCHMappingList-TDD
  } OPTIONAL, -- Rel-8 or later @sic R5-110104 sic@
  relAspTypeExtension SEQUENCE{}	OPTIONAL	-- Rel-10 or later @sic R5-130613 sic@
}

--**************************************************************
--
-- TrCH-LogicalChannelMapping
--   When used for logical channel to MAC-d flow mapping dl-LogicalChannelMapping shall be chosen,
--
--**************************************************************

TrCH-LogicalChannelMapping ::= SEQUENCE {
  logicalChannel-Mapping CHOICE {
    ul-LogicalChannelMapping SS-UL-LogicalChannelMapping,
    dl-LogicalChannelMapping SS-DL-LogicalChannelMapping
  },
  rB-Identity INTEGER (-31..32) OPTIONAL,
  cn-DomainIdentity CN-DomainIdentity OPTIONAL
}

--**************************************************************
--
-- TrCH-LogicalChannelMapping-TDD
--   When used for logical channel to MAC-d flow mapping dl-LogicalChannelMapping shall be chosen,
--  @sic R5-134957 R5w130320: TDD TTCN-2/3 differences sic@
--
--**************************************************************

TrCH-LogicalChannelMapping-TDD ::= SEQUENCE {
  logicalChannel-Mapping CHOICE {
    ul-LogicalChannelMapping SS-UL-LogicalChannelMapping-TDD, -- @sic R5-134957 R5w130320 sic@
    dl-LogicalChannelMapping SS-DL-LogicalChannelMapping
  },
  rB-Identity INTEGER (-31..32) OPTIONAL,
  cn-DomainIdentity CN-DomainIdentity OPTIONAL
}

--**************************************************************
--
-- TrChConfigType
--
--**************************************************************


TrChConfigType ::= CHOICE {
  nonDch NULL,
  dch ENUMERATED {normal(0), softHO(1)}
} 

--**************************************************************
--
-- UE-Info
--   The value of c-RNTI-DSCH-RNTI is 16 bits, used either for C-RNTI or DSCH-RNTI. DSCH is configured if the physical channel in CMAC-config-REQ is a PDSCH. Otherwise, C-RNTI is applied. For MAC-hs configuration both u-RNTI and c-RNTI-DSCH-RNTI are omitted.
--
--**************************************************************

UE-Info ::= SEQUENCE {
  u-RNTI U-RNTI OPTIONAL,
  c-RNTI C-RNTI OPTIONAL
}

--**************************************************************
--
-- UE-OperationMode
--
--**************************************************************

UE-OperationMode ::= ENUMERATED { opModeA (0), opModeC (1) }

--**************************************************************
--
-- RabTxInfo
--   Provide test data, number of RBs, and RB Tx info of each RB (RB id, SDU size and number of SDUs) to be transmitted in consecutive TTIs
--
--**************************************************************

RabTxInfo ::= SEQUENCE
{
  testData BIT STRING (SIZE (8..163840)),
  rbTxInfoList SEQUENCE (SIZE (1..6)) OF RbTxInfo
}

--**************************************************************
--
-- RbTxInfo
--   Info on RB id and the actual DL test data size (SDU-Size * number of SDUs). The actual test data is extracted from the first (SDU-Size * number of SDUs) bits in the raw testData buffer. SS shall transmit the actual test data in every TTI.The value nomOfSdu = T / TTI , whereby T=1200 is the duration of the data transmitting in the RAB test, taking into account the test tolerance (+50%) of the UE loop back delay (<800 ms).
--
--**************************************************************

RbTxInfo ::= SEQUENCE
{
  rB-Identity INTEGER(-31..32),
  sduSize INTEGER(1..163840),
  nomOfSdu INTEGER(0..255) -- 0 is set for no data on this RB
}

--**************************************************************
--
-- DDI-Mapping
--   Both SRBs and RBs can be mapped onto E-DCH. The mechanism for control of MAC header manipulation (macHeaderManipulation) is applied to individual logical channels to be mapped on E-DCH. Typically, the SRBs are configured in 'NormalMacHeader" mode while the RBs in user plane can be configured either in 'NormalMacHeader" or in "OmitMacHeader" mode.
--   If more than one UL RLC PDU size is configured for the RB (represent by logicalChannelIdentity), the different sizes will use subsequent DDI values starting from the DDI value in this table.
--   If the value of macHeaderManipulation field is 'NormalMacHeader', then data received on the E-DCH MACd flows supporting this logical channel shall have it's MAC header inspected to determine the appropriate routing, and removed as normal. The MACes  SDU shall be passed to the appropriate logical channel.
--   If the value of macHeaderManipulation field is 'OmitMacHeader', then data received on the E-DCH MACd flows supporting this logical channel shall have it's MAC header inspected to determine the appropriate routing, then the MAC-es layer shall deliver the MAC-es SDU, SI and the related  CFN, subframe number, HARQ process identity to the appropriate logical channel. The TTCN receives these fields by RLC-MAC-es-DATA-IND, then these fields can be checked by the TTCN.
--   HARQ ID = CFN mod 4 for TTI=10ms;
--   HARQ ID = (5*CFN + subframe number) mod 8 for TTI=2ms
--
--**************************************************************

DDI-Mapping ::= SEQUENCE {
  macHeaderManipulation MAC-HeaderManipulation,
  logicalChannelIdentity LogicalChannelIdentity,
  e-DCH-MAC-d-FlowIdentity E-DCH-MAC-d-FlowIdentity,
  ddi DDI,
  rlc-PDU-SizeList RLC-PDU-SizeList,
  includeInSchedulingInfo BOOLEAN,
  mac-LogicalChannelPriority MAC-LogicalChannelPriority,
  logicalChannelType LogicalChannelType,
  rB-Identity INTEGER    (-31..32)    OPTIONAL
}

--**************************************************************
--
-- DDI-MappingList
--
--**************************************************************

DDI-MappingList ::= SEQUENCE (SIZE (1..31)) OF DDI-Mapping

--**************************************************************
--
-- MACeConfig
--   If the macHeaderManipulation field is 'NormalMacHeader' in ddiMappingList, then data received on the E-DCH (MAC-e PDU) shall have it's MAC header inspected to de-multiplex and to determine the appropriate routing, and  the MACes  PDU shall be passed to the MAC-es together with the relevant DDI, N, CFN and subframe number.
--   If the macHeaderManipulation field field is 'OmitMacHeader', then data received on the E-DCH (MAC-e PDU) shall have it's MAC header inspected to de-multiplex and to determine the appropriate routing, then the MAC-e layer shall delivery the MAC-es PDU, SI and the related  CFN, subframe number to the MAC-es entity.
--   connectedToMAC-es field is used to provide the possibility that the E-DCH-MACdFlows from only one MAC-e entity are connected to the MAC-es entity in the inter node B soft handover test cases.
--   The IEs ddiMappinglist and e-DCHMacdFlows can be OMITted when changing the serving cell MAC-e without modification of MAC-e configurations. It will be applied in EDCH SHO.
--
--**************************************************************

MACeConfig ::= SEQUENCE {
  activationTime SS-ActivationTime,
  ddiMappinglist DDI-MappingList OPTIONAL,
  e-DCHMacdFlows E-DCHMACdFlows OPTIONAL,
  connectedToMAC-es BOOLEAN DEFAULT TRUE, -- can be set to FALSE in inter nodeB SHO
  ss-DRX-MAC-Info SS-DRX-MAC-Info OPTIONAL
}

--**************************************************************
--
-- MACeConfig-TDD
--   If the macHeaderManipulation field is 'NormalMacHeader' in ddiMappingList, then data received on the E-DCH (MAC-e PDU) shall have it's MAC header inspected to de-multiplex and to determine the appropriate routing, and  the MACes  PDU shall be passed to the MAC-es together with the relevant DDI, N, CFN and subframe number.
--   If the macHeaderManipulation field field is 'OmitMacHeader', then data received on the E-DCH (MAC-e PDU) shall have it's MAC header inspected to de-multiplex and to determine the appropriate routing, then the MAC-e layer shall delivery the MAC-es PDU, SI and the related  CFN, subframe number to the MAC-es entity.
--   connectedToMAC-es field is used to provide the possibility that the E-DCH-MACdFlows from only one MAC-e entity are connected to the MAC-es entity in the inter node B soft handover test cases.
--   The IEs ddiMappinglist and e-DCHMacdFlows can be OMITted when changing the serving cell MAC-e without modification of MAC-e configurations. It will be applied in EDCH SHO.
--
--**************************************************************

MACeConfig-TDD ::= SEQUENCE {
  activationTime SS-ActivationTime,
  ddiMappinglist DDI-MappingList OPTIONAL,
  e-DCHMacdFlows E-DCHMACdFlows-TDD OPTIONAL
}

--**************************************************************
--
-- MACesConfig
--   MACesConfig establishes the mapping between logical channels and E-DCH-MACd-Flows.
--   When the macTestMode is TRUE, the re-ordering entity shall not elimilate the deplicated packets, but passes them to RLC. macTestMode = "TRUE" is used for testing the retransmission function of HARQ process
--
--**************************************************************

MACesConfig ::= SEQUENCE {
  activationTime SS-ActivationTime,
  ddiMappinglist DDI-MappingList,
  macTestMode BOOLEAN DEFAULT FALSE
}

--**************************************************************
--
-- ModulationScheme
--
--**************************************************************

ModulationScheme ::= ENUMERATED {qpsk (0), qam16 (1), qam64 (2), spare1 (3)}

--**************************************************************
--
-- RedundancyVersionList
--   Gives the Redundancy and constellation version coding sequence (Xrv) to be used for each transmission / retransmission. The SIZE (number of Xrv elements in there) of the SEQUENCE implies the number of HARQ transmission / retransmissions to be required.
--
--**************************************************************

RedundancyVersionList ::= SEQUENCE (SIZE (1..8)) OF INTEGER (0..7)

--**************************************************************
--
-- LCR TDD ONLY START
--
--**************************************************************
--**************************************************************
--
-- TimeSlotConfiguration-LCR
--
--**************************************************************

TimeSlotConfiguration-LCR ::= SEQUENCE {
  timeSlotLCR         TimeslotNumber-LCR-r4,
  timeSlotStatus     ENUMERATED {active(0), notActive(1)},
  timeSlotDirection     ENUMERATED {downlink(0), uplink(1)}
}

--**************************************************************
--
-- TimeSlotConfigurationList-LCR
--
--**************************************************************

TimeSlotConfigurationList-LCR ::= SEQUENCE (SIZE (1..maxTS-LCR)) OF TimeSlotConfiguration-LCR

--**************************************************************
--
-- SecondaryFrequencyInfoList
--
--**************************************************************

SecondaryFrequencyInfoList ::= SEQUENCE (SIZE(1..maxNumOfSecondFrequency)) OF SecondaryFrequencyInfo

--**************************************************************
--
-- SecondaryFrequencyInfo
--
--**************************************************************

SecondaryFrequencyInfo ::= SEQUENCE {
  frequencyInfo          UARFCN,
  dLTxAttenuationLevel   INTEGER(0..30)
}

--**************************************************************
--
-- DwPCHInfo
--
--**************************************************************

DwPCHInfo ::= SEQUENCE {
    tstd-Indicator     ENUMERATED {notApplied(0),applied(1)},
    dwPCH-Power     DwPCH-Power
}

--**************************************************************
--
-- TransmissionDiversityApplied
--
--**************************************************************

TransmissionDiversityApplied ::= ENUMERATED {notApplied(0), applied(1)}

--**************************************************************
--
-- SS-Non-ScheduledTransGrantInfoTDD
--   Rel-7 or later.
--
--**************************************************************

SS-Non-ScheduledTransGrantInfoTDD ::= CHOICE {
  tdd384-768 SEQUENCE
  {
    timeslotResourceRelatedInfo BIT STRING (SIZE (13 ) ), 
    powerResourceRelatedInfo     INTEGER (1..32 ), 
    activationTime         ActivationTime, 
    repetitionPeriodAndLength     RepetitionPeriodAndLength OPTIONAL, 
    codeResourceInfo         UL-TS-ChannelisationCode
  }, 
  tdd128 SEQUENCE
  {
    n-E-UCCH             INTEGER (1..8 ) OPTIONAL, 
    n-E-HICH             INTEGER (4..15 ) OPTIONAL, 
    timeslotResourceRelatedInfo BIT STRING (SIZE (5 ) ), 
    powerResourceRelatedInfo     INTEGER (1..32 ), 
    activationTime         ActivationTime, 
    sfnNum             INTEGER (0..1 ), 
    repetitionPeriodAndLength     RepetitionPeriodAndLength OPTIONAL, 
    codeResourceInfo         UL-TS-ChannelisationCode, 
    e-HICH-Info SEQUENCE
    {
      e-HICH-ID-TDD             INTEGER (0..255 ), 
      signature-Sequence-Group-Index     INTEGER (0..19 )
    }
  }
}

--**************************************************************
--
-- LCR TDD ONLY END
--
--**************************************************************
--**************************************************************
--
-- CMAC-Ciphering-Activate-CNF
--   To confirm to activate or inactivate the ciphering
--
--**************************************************************

CMAC-Ciphering-Activate-CNF ::= SEQUENCE {
  cellId INTEGER (-1..63),
  routingInfo RoutingInfo
}

--**************************************************************
--
-- CMAC-Ciphering-Activate-REQ
--   To request to start or, restart or stop downlink ciphering or uplink deciphering. The physicalChannelIdentity of DPCH applies to routingInfo.Do not increment HFN part of COUNT-C if the value of incrementCOUNT-C-Ind is "NotIncr".
--
--**************************************************************

CMAC-Ciphering-Activate-REQ ::= SEQUENCE
{
  cellId INTEGER (-1..63),
  routingInfo RoutingInfo,
  ratType RatType,
  cn-DomainIdentity CN-DomainIdentity,
  cipheringModeInfo CipheringModeInfo OPTIONAL,
  cipheringModeInfo-r7 CipheringModeInfo-r7 OPTIONAL,
  incHFN Increment-Mode
}

--**************************************************************
--
-- CMAC-Config-CNF
--   For MAC emulator to report that a previous attempt to setup, reconfigure or release a logical channel is successful.
--
--**************************************************************

CMAC-Config-CNF ::= SEQUENCE {
  cellId INTEGER (-1..63),
  routingInfo RoutingInfo
}

--**************************************************************
--
-- CMAC-Config-FDD-REQ
--   To request to configure MAC entity. Setup is used for creation of the MAC instances or the MAC resources. Release is used for free  the all MAC resources. The reconfiguration is to change the MAC parameters, it is not the MAC modification.
--
--**************************************************************

CMAC-Config-FDD-REQ ::= SEQUENCE {
  cellId INTEGER (-1..63),
  routingInfo RoutingInfo,
  ratType RatType,
  configMessage CHOICE {
    setup CmacConfigReq-FDD,
    reconfigure CmacConfigReq-FDD,
    release SS-ActivationTime
  }
}

--**************************************************************
--
-- CMAC-Config-TDD-REQ
--   To request to configure MAC entity. Setup is used for creation of the MAC instances or the MAC resources. Release is used for free  the all MAC resources. The reconfiguration is to change the MAC parameters, it is not the MAC modification.
--
--**************************************************************

CMAC-Config-TDD-REQ ::= SEQUENCE {
  cellId INTEGER (-1..63),
  routingInfo RoutingInfo,
  ratType RatType,
  configMessage CHOICE {
    setup CmacConfigReq-TDD,
    reconfigure CmacConfigReq-TDD,
    release SS-ActivationTime 
  }
}

--**************************************************************
--
-- CMAC-PAGING-Config-CNF
--   To confirm to setup the Paging message
--
--**************************************************************

CMAC-PAGING-Config-CNF ::= SEQUENCE {
  cellId INTEGER (0..63),
  routingInfo RoutingInfo
}

--**************************************************************
--
-- CMAC-PAGING-Config-FDD-REQ
--   To request MAC layer to send the Paging message on the specified configuration.
--   CMAC-PAGING-Config-REQ in TTCN-2
--
--**************************************************************

CMAC-PAGING-Config-FDD-REQ ::= SEQUENCE {
  cellId INTEGER (0..63),
  routingInfo RoutingInfo,
  ratType RatType,
  configMessage CmacPagingConfigReq
}

--**************************************************************
--
-- CMAC-PAGING-Config-TDD-REQ
--   To request MAC layer to send the Paging message on the specified configuration.
--   CMAC-PAGING-Config-REQ in TTCN-2
--
--**************************************************************

CMAC-PAGING-Config-TDD-REQ ::= SEQUENCE {
  cellId INTEGER (0..63),
  routingInfo RoutingInfo,
  ratType RatType,
  configMessage CmacPagingConfigReq-TDD
}
--**************************************************************
--
-- CMAC-SYSINFO-Config-CNF
--   To confirm to setup the BCCH message to MAC layer
--
--**************************************************************

CMAC-SYSINFO-Config-CNF ::= SEQUENCE {
  cellId INTEGER (0..63),
  routingInfo RoutingInfo
}

--**************************************************************
--
-- CMAC-SYSINFO-Config-REQ
--   To request MAC layer to send the BCCH message on the specified configuration.
--
--**************************************************************

CMAC-SYSINFO-Config-REQ ::= SEQUENCE {
  cellId INTEGER (0..63),
  routingInfo RoutingInfo,
  ratType RatType,
  configMessage CmacSysinfoConfigReq
}

--**************************************************************
--
-- CMAC-SecurityMode-Config-CNF
--   To confirm to configure the MAC security mode
--
--**************************************************************

CMAC-SecurityMode-Config-CNF ::= SEQUENCE {
  cellId INTEGER (-1..63)
}

--**************************************************************
--
-- CMAC-SecurityMode-Config-REQ
--   To request to configure the MAC security mode
--   If there are several CMAC-Ciphering-Activate-REQ follow this ASP, the SS shall take a serial of specified actions on the same contents in this ASP at the activation time indicated in each CMAC-Ciphering-Activate-REQ.
--
--**************************************************************

CMAC-SecurityMode-Config-REQ ::= SEQUENCE {
  cellId INTEGER (-1..63),
  macCipheringInfo SecurityInfo
}

--**************************************************************
--
-- CPHY-Cell-Config-CNF
--   To confirm to setup the cell parameter
--
--**************************************************************

CPHY-Cell-Config-CNF ::= SEQUENCE {
  cellId INTEGER (0..63)
}

--**************************************************************
--
-- CPHY-Cell-Config-FDD-REQ
--   To request to setup the cell parameter.
--   The unit of tcell is chip; the unit of sfnOffset is frame number. The sfnOffset is defined as the number of frames the SFN shall be shifted, i.e the frames lagging behind or in advance, in comparison to a system reference time. The both interpretations are valid for the test.
--   The primary scrambling code number of the cell is 16*primaryScramblingCode-SS; the unit of dLTxAttenuationLevel is dB.
--
--**************************************************************

CPHY-Cell-Config-FDD-REQ ::= SEQUENCE {
  cellId INTEGER (0..63),
  tcell INTEGER(0..38399),
  sfnOffset INTEGER (0 .. 4095 ),
  frequencyInfo FrequencyInfo,
  primaryScramblingCode-SS INTEGER (0..511),
  cellTxPowerLevel CellTxPowerLevel,
  dLTxAttenuationLevel INTEGER(0..30|123),
  frequencyBandIndicator FrequencyBandFDD,
  relAspTypeExtension SEQUENCE{} OPTIONAL	-- Rel-10 or later @sic R5-130618 sic@
}

--**************************************************************
--
-- CPHY-Cell-Config-TDD-REQ
--   To request to setup the cell parameter.
--   the unit of dLTxAttenuationLevel is dB.
--   CPHY-Cell-Config-REQ in TTCN-2
--
--**************************************************************

CPHY-Cell-Config-TDD-REQ ::= SEQUENCE {
  cellId             INTEGER (0..63),
  sfnOffset             INTEGER (0 .. 4095 ),
  frequencyInfo         FrequencyInfo,  
  cellTxPowerLevel         CellTxPowerLevel,
  dLTxAttenuationLevel         INTEGER(0..30|123),
  cellParametersID          CellParametersID,
  timeSlotConfigurationList-LCR TimeSlotConfigurationList-LCR,
  dwPCHInfo                     DwPCHInfo,
  transmissionDiversityApplied  ENUMERATED {notApplied(0),applied(1)}   OPTIONAL,
  secondaryFrequencyInfo        SecondaryFrequencyInfoList  OPTIONAL,
  upPCHposition                 UpPCHposition-LCR OPTIONAL,
  relAspTypeExtension 			SEQUENCE{} OPTIONAL -- Rel-10 or later
}

--**************************************************************
--
-- CPHY-Cell-Release-CNF
--   The confirmation to the CPHY-Cell-Release-Req
--
--**************************************************************

CPHY-Cell-Release-CNF ::= SEQUENCE {
  soft-Reset BOOLEAN,
  cell-ID-List SEQUENCE (SIZE (1..8)) OF INTEGER (0..63) -- cell IDs
}

--**************************************************************
--
-- CPHY-Cell-Release-REQ
--   1. This Primitive with "Soft-Reset" flag ON gives a common known starting point/state of SS for a test case. The SS performs the following whenever it receives this primitive with "Soft-Reset" flag ON:Releases all configured Channels and cells (if any) irrespective of Cell ID list IE.
--   2. Releases the associated Memory Buffers (if any).
--   3. Cancels all active timers (if any)
--   With "Soft-Reset" flag  OFF:
--   1. Releases cells listed in IE Cell-ID-List and  associated configured Channels (if any)
--   2. Releases the Memory Buffers(if any) associated with Cells listed in IE Cell-ID-List
--   3. Cancels all active timers (if any) associated with Cells listed in IE Cell-ID-List.
--
--**************************************************************

CPHY-Cell-Release-REQ ::= SEQUENCE {
  soft-Reset BOOLEAN,
  cell-ID-List SEQUENCE (SIZE (1..8)) OF INTEGER (0 .. 63), -- @sic R5-112591 sic@
  rb-Config-List SEQUENCE (SIZE (1..8)) OF INTEGER OPTIONAL -- @sic R5-112591 sic@
}

--**************************************************************
--
-- CPHY-Cell-TxPower-Modify-CNF
--   To confirm to change the DL power
--
--**************************************************************

CPHY-Cell-TxPower-Modify-CNF ::= SEQUENCE {
  cellId INTEGER (0..63)
}

--**************************************************************
--
-- CPHY-Cell-TxPower-Modify-REQ
--   To request to change the DL power
--
--**************************************************************

CPHY-Cell-TxPower-Modify-REQ ::= SEQUENCE {
  cellId INTEGER (0..63),
  dLTxAttenuationLevel INTEGER(0..40|123) 
}

--**************************************************************
--
-- CPHY-Frame-Number-CNF
--   To return the requested  connection frame number. The routingInfo indicates a physical channel.
--
--**************************************************************

CPHY-Frame-Number-CNF ::= SEQUENCE{
  cellId INTEGER (0..63),
  routingInfo RoutingInfo,
  frameNumber INTEGER (0..255)
}

--**************************************************************
--
-- CPHY-Frame-Number-REQ
--   To request the physical layer to return a connection frame number  on which the next message can be sent  at the specified PCO on the specified logical channel. The return frame number shall leave time from current frame number in order to leave some execution time for TTCN preparing next message. The routingInfo indicates a physical channel
--
--**************************************************************

CPHY-Frame-Number-REQ ::= SEQUENCE{
  cellId INTEGER (0..63),
  routingInfo RoutingInfo
}

--**************************************************************
--
-- CPHY-Ini-CNF
--   Confirm the test initialisation
--
--**************************************************************

CPHY-Ini-CNF ::= SEQUENCE
{
  confirmation NULL
}

--**************************************************************
--
-- CPHY-Ini-REQ
--   Request to initialise the test
--
--**************************************************************

CPHY-Ini-REQ ::= ENUMERATED {
  defaultRadioEnvironment(0),
  nonDefaultMultiCell(1)
}

--**************************************************************
--
-- CPHY-Out-of-Sync-IND
--   To report that the physical channel synchronization (in FDD mode, sync with uplink DPCCH) was lost as detected by the SS receiver.
--
--**************************************************************

CPHY-Out-of-Sync-IND ::= SEQUENCE {
  cellId INTEGER (0..63),
  routingInfo RoutingInfo
}

--**************************************************************
--
-- CPHY-RL-Modify-CNF
--   To confirm to modify the Radio Link
--
--**************************************************************

CPHY-RL-Modify-CNF ::= SEQUENCE {
  cellId INTEGER (0..63),
  routingInfo RoutingInfo
}

--**************************************************************
--
-- CPHY-RL-Modify-FDD-REQ
--   To request to modify the Radio Link
--   HardHandover (PhysicalChannelReconfig)
--   ChannelisationCodeChange
--   FrequencyChange
--   PhysicalChannelModifyForTrCHReconfig
--   CompressedMode( PhysicalChannelReconfig)
--   Re-Synchronized HardHandover
--   Softhandover
--
--**************************************************************

CPHY-RL-Modify-FDD-REQ ::= SEQUENCE {
  cellId INTEGER (0..63),
  routingInfo RoutingInfo,
  ratType RatType,
  modifyMessage CphyRlModifyReq-FDD
}

--**************************************************************
--
-- CPHY-RL-Modify-TDD-REQ
--   To request to modify the Radio Link
--   HardHandover (PhysicalChannelReconfig)
--   ChannelisationCodeChange
--   FrequencyChange
--   PhysicalChannelModifyForTrCHReconfig
--   CompressedMode( PhysicalChannelReconfig)
--   Re-Synchronized HardHandover
--   CPHY-RL-Modify-REQ in TTCN-2
--
--**************************************************************

CPHY-RL-Modify-TDD-REQ ::= SEQUENCE {
  cellId INTEGER (0..63),
  secondaryFrequency UARFCN OPTIONAL,
  routingInfo RoutingInfo,
  ratType RatType,
  modifyMessage CphyRlModifyReq-TDD
}

--**************************************************************
--
-- CPHY-RL-Release-CNF
--   PHY emulator confirms that a specified physical channel has been released.
--
--**************************************************************

CPHY-RL-Release-CNF ::= SEQUENCE {
  cellId INTEGER (0..63),
  routingInfo RoutingInfo
}

--**************************************************************
--
-- CPHY-RL-Release-FDD-REQ
--   To request to release the Radio Link
--
--**************************************************************

CPHY-RL-Release-FDD-REQ ::= SEQUENCE {
  cellId INTEGER (0..63),
  routingInfo RoutingInfo,
  activationTime SS-ActivationTime 
}

--**************************************************************
--
-- CPHY-RL-Release-TDD-REQ
--   To request to release the Radio Link
--
--**************************************************************

CPHY-RL-Release-TDD-REQ ::= SEQUENCE {
  cellId INTEGER (0..63),
  routingInfo RoutingInfo,
  activationTime SS-ActivationTime OPTIONAL
}

--**************************************************************
--
-- CPHY-RL-Setup-CNF
--   To confirm to setup the Radio Link
--
--**************************************************************

CPHY-RL-Setup-CNF ::= SEQUENCE {
  cellId INTEGER (0..63),
  routingInfo RoutingInfo
}

--**************************************************************
--
-- CPHY-RL-Setup-FDD-REQ
--   To request to setup the associated transport channels and the Radio Link itself.
--   CPHY-RL-Setup-REQ in TTCN-2
--
--**************************************************************

CPHY-RL-Setup-FDD-REQ ::= SEQUENCE {
  cellId INTEGER (0..63),
  routingInfo RoutingInfo,
  ratType RatType,
  setupMessage CphyRlSetupReq-FDD
}

--**************************************************************
--
-- CPHY-RL-Setup-TDD-REQ
--   To request to setup the associated transport channels and the Radio Link itself.
--   CPHY-RL-Setup-REQ in TTCN-2
--
--**************************************************************

CPHY-RL-Setup-TDD-REQ ::= SEQUENCE {
  cellId INTEGER (0..63),
  secondaryFrequency UARFCN OPTIONAL,
  routingInfo RoutingInfo,
  ratType RatType,
  setupMessage CphyRlSetupReq-TDD
}

--**************************************************************
--
-- CPHY-Sync-IND
--   To indicate that physical channel synchronization (in FDD mode, sync with DPCCH) has been achieved.
--
--**************************************************************

CPHY-Sync-IND ::= SEQUENCE{
  cellId INTEGER (0..63),
  routingInfo RoutingInfo
}

--**************************************************************
--
-- CPHY-TrCH-Config-CNF
--   To confirm to configure the transport channel
--
--**************************************************************

CPHY-TrCH-Config-CNF ::= SEQUENCE {
  cellId INTEGER (0..63),
  routingInfo RoutingInfo
}

--**************************************************************
--
-- CPHY-TrCH-Config-FDD-REQ
--   To request to configure the transport channel
--
--**************************************************************

CPHY-TrCH-Config-FDD-REQ ::= SEQUENCE {
  cellId INTEGER (0..63),
  routingInfo RoutingInfo,
  ratType RatType,
  trchConfigType TrChConfigType,
  configMessage CphyTrchConfigReq
}

--**************************************************************
--
-- CPHY-TrCH-Config-TDD-REQ
--   To request to configure the transport channel
--
--**************************************************************

CPHY-TrCH-Config-TDD-REQ ::= SEQUENCE {
  cellId INTEGER (0..63),
  routingInfo RoutingInfo,
  ratType RatType,
  trchConfigType TrChConfigType,
  configMessage CphyTrchConfigReq-TDD
}

--**************************************************************
--
-- CPHY-TrCH-Release-CNF
--   To confirm to release tthe Radio Link
--
--**************************************************************

CPHY-TrCH-Release-CNF ::= SEQUENCE {
  cellId INTEGER (0..63),
  routingInfo RoutingInfo
}

--**************************************************************
--
-- CPHY-TrCH-Release-FDD-REQ
-- CPHY-TrCH-Release-TDD-REQ
--   To request to release tthe Radio Link
--
--**************************************************************

CPHY-TrCH-Release-FDD-REQ ::= SEQUENCE {
  cellId INTEGER (0..63),
  routingInfo RoutingInfo,
  trchConfigType TrChConfigType,
  activationTime SS-ActivationTime
}

CPHY-TrCH-Release-TDD-REQ ::= SEQUENCE {
  cellId INTEGER (0..63),
  routingInfo RoutingInfo,
  trchConfigType TrChConfigType,
  activationTime SS-ActivationTime OPTIONAL
}

--**************************************************************
--
-- CPHY-HS-DPCCH-CQI-MultiCell-CNF
--   To Confirm CPHY-HS-DPCCH-CQI-MultiCell-REQ
--
--**************************************************************
CPHY-HS-DPCCH-CQI-MultiCell-CNF ::= SEQUENCE	{
	cellId				INTEGER(0..63)
}

--**************************************************************
--
-- CPHY-HS-DPCCH-CQI-MultiCell-REQ
--  To enable the SS to start reporting N times of the CQI value received on the HS-DPCCH on cellId when 3C/4C-HSDPA is configured. After N times the SS stops reporting. N is specified as numberOfReports.
--  At the SS initialization reporting of CQI values is disabled.
--
--**************************************************************
CPHY-HS-DPCCH-CQI-MultiCell-REQ ::= SEQUENCE	{
	cellId					INTEGER(0..63),
	ratType					RatType,
	numberOfReports			INTEGER(1..32)
}

--**************************************************************
--
-- CPHY-HS-DPCCH-CQI-MultiCell-IND
--  SS generates one indication per subframe when a CQI/PCI value is received on HS-DPCCH after invocation of ASP CPHY-HS-DPCCH-CQI-MultiCell-REQ and before the numberOfReports is reached.
--  This ASP is used for verifying whether the UE has configured the HS-DSCH and starts reception of HS-DSCH (3GPP TS 25.331 [21], subclause 8.6.6.34 and 3GPP TS 25.212 [58], subclause 4.7.4.2).
--
--**************************************************************
CPHY-HS-DPCCH-CQI-MultiCell-IND ::= SEQUENCE	{
	cellId				INTEGER(0..63),
	ratType				RatType,
	cfn					INTEGER (0..255),
	subframe			INTEGER (0..4),
	cqiPci-List			CqiPci-List-Type
}

CqiPci-List-Type ::= SEQUENCE (SIZE (1..2)) OF CqiPci-Type

CqiPci-Type ::= SEQUENCE	{
	cqi			INTEGER (0..1023),   
	pci			INTEGER (0..3) OPTIONAL,						-- MIMO
	cqiType		ENUMERATED {cqiTypeA(0), cqiTypeB(1)} OPTIONAL	-- MIMO
}

--**************************************************************
--
-- CPHY-HS-DPCCH-CQI-CNF
--   Applicable Rel-5 or later
--   To Confirm CPHY-HS-DPCCH-CQI-REQ
--
--**************************************************************
CPHY-HS-DPCCH-CQI-CNF ::= SEQUENCE	{
	cellId				INTEGER(0..63)
}

--**************************************************************
--
-- CPHY-HS-DPCCH-CQI-REQ
--  Applicable Rel-5 or later
--  To enable the SS to start reporting N times of the CQI value received on the HS DPCCH. After N times the SS stops reporting. N is specified in numberOfReports.
--  At the SS initialization reporting of CQI values is disabled
--
--**************************************************************
CPHY-HS-DPCCH-CQI-REQ ::= SEQUENCE	{
	cellId					INTEGER(0..63),
	ratType					RatType,
	numberOfReports			INTEGER(1..32)
}

--**************************************************************
--
-- CPHY-HS-DPCCH-CQI-IND
--  Applicable Rel-5 or later
--  SS generates the indication when a CQI value is received on HS-DPCCH after invocation of ASP CPHY-HS-DPCCH-CQI-REQ and before the numberOfReports is reached.
--  This ASP is used for verifying whether the UE has configured the HS-DSCH and starts reception of HS-DSCH (3GPP TS 25.331 [21], subclause 8.6.6.34).
--  'second-cqi' shall be reported when MIMO is configured and dual transport block type A CQI report is received. When second-cqi is present, allowed values for 'cqi' are 0..14.
--  In all other cases (i.e. non MIMO operation, MIMO operation but with CQI type B or single transport block type A CQI reports] 'second-cqi' shall not be reported and range for cqi is 0..30.
--  'pci' and cqiType shall be present when MIMO is configured.
--
--**************************************************************
CPHY-HS-DPCCH-CQI-IND ::= SEQUENCE	{
	cellId				INTEGER(0..63),
	ratType				RatType,
	cfn					INTEGER (0..255),
	subframe			INTEGER (0..4),
	cqi				    INTEGER (0..30),
    cqiExt			    CQI-ExtensionType
}

--**************************************************************
--
-- CQI-ExtensionType
--  Rel-7 or later
--  The value -1 for second-cqi indicates the absence of the second CQI.
--
--**************************************************************
CQI-ExtensionType ::= SEQUENCE	{
	second-cqi		INTEGER (-1..14) OPTIONAL,
	pci				INTEGER (0..3) OPTIONAL,						-- MIMO
	cqiType			ENUMERATED {cqiTypeA(0), cqiTypeB(1)} OPTIONAL	-- MIMO
}

--**************************************************************
--
-- CPHY-MeasurementConfig-REQ
-- To configure measurement parameters
-- cellDCHMeasOccasionInfo-TDD128: to configure SS for CELL-DCH measurement occasion according to TS 25.331[21] clause 8.5.11a and 8.6.7.26. No DL transmission shall be performed in the calculated timeslot. The activationTime  is set to 'activateNow'.
--
--**************************************************************
CPHY-MeasurementConfig-REQ ::=	SEQUENCE {
		cellId					INTEGER(0..63),
		activationTime			SS-ActivationTime,
		measurement		CHOICE {
			rel9	SEQUENCE {
				cellDCHMeasOccasionInfo-TDD128	CellDCHMeasOccasionInfo-TDD128-r9 
				-- LCR TDD Rel9
			}
		}
	}

--**************************************************************
--
-- CPHY-MeasurementConfig-CNF
--  Confirm a previous CPHY-MeasurementConfig-REQ being successful.
--
--**************************************************************
CPHY-MeasurementConfig-CNF ::= SEQUENCE {
		cellId		INTEGER(0..63)
	}

	
--**************************************************************
--
--	CPHY-AICH-NegAckModeSet-REQ
--  To configure SS to transmit a specific number of Negative AICH Acknowledge
--   - numNegACK defines how many access preambles are negatively acknowledged
--   - nextAICH-Mod is the AICH acknowledgement mode applied after the numNegACK negative acknowledgements have been transmitted.
--
--**************************************************************	
CPHY-AICH-NegAckModeSet-REQ ::= SEQUENCE	{
	cellId			INTEGER(0..63),
	routingInfo		RoutingInfo,
	ratType			RatType,
	numNegACK		INTEGER(1..100),
	nextAICH-Mode	AICH-Mode
}

--**************************************************************
--
-- Normal operation: The AICH will operate as normal, and will acknowledge or negatively acknowledge on all UE RACH/E-DCH transmission attempts, appropriately.
-- No Acknowledge: The AICH shall not transmit acknowledge or Negative Acknowledge on all UE RACH/E-DCH transmission attempts.
-- Negative Acknowledge: The AICH shall transmit Negative Acknowledge on all UE RACH/E-DCH transmission attempts
--
--**************************************************************	
AICH-Mode ::= ENUMERATED	{
			normal	(0),
			noAck	(1),
			negACK	(2)
}

--**************************************************************
--
--	CPHY-AICH-NegAckModeSet-CNF
--  To confirm setting of Negative AICH Acknowledge Mode
--
--**************************************************************	
CPHY-AICH-NegAckModeSet-CNF ::= SEQUENCE	{
	cellId			INTEGER(0..63),
	routingInfo		RoutingInfo
}


--**************************************************************
--
-- CPHY-PRACH-Measurement-REQ
-- To request for Start or Stop of PRACH Measurements to be done every PRACH PREAMBLE or MESSAGE received.
-- If reportSFN is set to TRUE, SS shall report in the IE PRACH-MeasurementReport the SFN value at which the event is received.
-- 
--**************************************************************
CPHY-PRACH-Measurement-REQ ::= SEQUENCE	{
  cellId       INTEGER(0..63),
  routingInfo  RoutingInfo,
  ratType      RatType,
  pRACH-MeasurementInd   PRACH-MeasurementInd,
  reportSFN              BOOLEAN DEFAULT FALSE
}

--**************************************************************
--
-- CPHY-PRACH-Measurement-CNF
-- To Confirm PRACH Measurement Req
--
--**************************************************************
CPHY-PRACH-Measurement-CNF ::= SEQUENCE	{
			cellId				INTEGER(0..63),
			routingInfo			RoutingInfo
}

--**************************************************************
-- PRACH-MeasurementInd
-- 1)	StartMeas: The SS shall start the sending PRACH parameters Measurement report on CPHY PCO, for each PRACH Preamble or MESSAGE received from the UE by primitive CPHY-PRACH-Measurement-Report-IND on CPHY PCO.
-- 2)	StopMeas: The SS shall stop sending of PRACH parameters Measurement report on CPHY PCO, for each PRACH Preamble or MESSAGE received from the UE by primitive CPHY-PRACH-Measurement-Report-IND on CPHY PCO.
--**************************************************************
PRACH-MeasurementInd ::= ENUMERATED	{
			startMeas (0),
			stopMeas (1)
}

--**************************************************************
-- 
-- CPHY-PRACH-Measurement-Report-IND
-- SS indicates a PRACH parameters measurement report for each PRACH Preambles or MESSAGE received from the UE
--
--**************************************************************
CPHY-PRACH-Measurement-Report-IND ::= SEQUENCE     {
	cellId			INTEGER(0..63),
	routingInfo		RoutingInfo,
	ratType			RatType,
	measurementReport	PRACH-MeasurementReport
}

--**************************************************************
-- PRACH-MeasurementReport
-- sfn is included if reportSFN is TRUE in CPHY-PRACH-Measurement-REQ.
--**************************************************************
PRACH-MeasurementReport ::= SEQUENCE	{
	usedPRACH-AcessSlot			INTEGER (0..14),
	usedPRACH-Signature			INTEGER (0..15)	OPTIONAL,
	sfn							INTEGER (0..4095) OPTIONAL
}


--**************************************************************
--
-- CRLC-Ciphering-Activate-CNF
--   To confirm to activate or inactivate the ciphering
--
--**************************************************************

CRLC-Ciphering-Activate-CNF ::= SEQUENCE {
  cellId INTEGER (-1..63)}

--**************************************************************
--
-- CRLC-Ciphering-Activate-REQ
--   To request to start, restart or stop downlink ciphering or uplink deciphering. The RB-identity applied to routingInfo indicates the SRB being not suspended during the execution of the ciphering mode command. Each call of the ASP includes one RLC SN in  rb-DL-CiphActivationTimeInfo for the corresponding rb-identity.
--
--**************************************************************

CRLC-Ciphering-Activate-REQ ::= SEQUENCE {
  cellId INTEGER (-1..63),
  ratType RatType,
  cn-DomainIdentity CN-DomainIdentity,
  ciphActivationInfo CiphActivationInfo,
  incHFN RLC-IncMode 
}

--**************************************************************
--
-- CRLC-Config-CNF
--   For RLC emulator to comfirm that a previous attempt to establish, reconfigure or release a radio bearer has been successful
--
--**************************************************************

CRLC-Config-CNF ::= SEQUENCE {
  cellId INTEGER (-1..63),
  routingInfo RoutingInfo
}

--**************************************************************
--
-- CRLC-Config-FDD-REQ
--   To request to setup, reconfigure or release RLC entity
--
--**************************************************************

CRLC-Config-FDD-REQ ::= SEQUENCE {
  cellId INTEGER (-1..63),
  routingInfo RoutingInfo,
  ratType RatType,
  configMessage CrlcConfigReq,
  activationTime SS-ActivationTime OPTIONAL
}

--**************************************************************
--
-- CRLC-Config-TDD-REQ
--   To request to setup, reconfigure or release RLC entity
--
--**************************************************************

CRLC-Config-TDD-REQ ::= SEQUENCE {
  cellId INTEGER (-1..63),
  routingInfo RoutingInfo,
  ratType RatType,
  configMessage CrlcConfigReq-TDD,
  activationTime SS-ActivationTime OPTIONAL
}

--**************************************************************
--
-- CRLC-Integrity-Activate-CNF
--   To confirm to activate or inactivate the integrity protection
--
--**************************************************************

CRLC-Integrity-Activate-CNF ::= SEQUENCE {
  cellId INTEGER (-1..63)
}

--**************************************************************
--
-- CRLC-Integrity-Activate-REQ
--   To request to start or to modify the downlink or uplink integrity protection. The ASP shall be called before the sending of SECURITY MODE COMMAND. It activates the integrity on all SRBs in DL. The ASP shall not be called if the integrity shall be switched off in the test case.
--
--**************************************************************

CRLC-Integrity-Activate-REQ ::= SEQUENCE {
  cellId INTEGER (-1..63),
  cn-DomainIdentity CN-DomainIdentity,
  integrityActivationInfo IntegrityActivationInfo
}

--**************************************************************
--
-- CRLC-Integrity-Failure-IND
--   RLC emulator reports the occurrences of a failure in integrity protection, i.e. reception of an integrity-protected RLC AM/UM SDU containing a non-matching X-MAC value compared to the desired.
--
--**************************************************************

CRLC-Integrity-Failure-IND ::= SEQUENCE {
  cellId INTEGER (-1..63),
  routingInfo RoutingInfo,
  failureCause ENUMERATED { codeNotMatched(0) }   
}

--**************************************************************
--
-- CRLC-ProhibitRLC-Ack-CNF
--   To confirm that the reception of a CRLC-ProhibitRLC-Ack-REQ.
--
--**************************************************************

CRLC-ProhibitRLC-Ack-CNF ::= SEQUENCE{
  cellId INTEGER (-1..63),
  routingInfo RoutingInfo,
  supportflag SupportFlag DEFAULT noNeed
}

--**************************************************************
--
-- CRLC-ProhibitRLC-Ack-REQ
--   To request the SS to prohibit/Continue acknowledging RLC SDUs.
--
--**************************************************************


CRLC-ProhibitRLC-Ack-REQ ::= SEQUENCE{
  cellId INTEGER (-1..63),
  routingInfo RoutingInfo,
  mode ENUMERATED{prohibit(0), continue(1)}
}

--**************************************************************
--
-- CRLC-RRC-MessageSN-CNF
--   To return the counter I value (HFN and RRC message sequence number) for sending the next DL RRC message or for receiving the next UL RRC message on the concerned SRB.
--   COUNT-I-MSB is the 28 MSB of the COUNT-I (HFN)
--
--**************************************************************

CRLC-RRC-MessageSN-CNF ::= SEQUENCE
{
  cellId INTEGER (-1..63),
  routingInfo RoutingInfo,
  count-I-MSB-UL COUNT-I-MSB,
  count-I-LSB-UL RRC-SequenceNumber,
  count-I-MSB-DL COUNT-I-MSB,
  count-I-LSB-DL RRC-SequenceNumber
}

--**************************************************************
--
-- CRLC-RRC-MessageSN-REQ
--   To request the SS to return the values in COUNT-I for sending the next DL RRC message or for receiving the next UL RRC message on the concerned SRB.
--
--**************************************************************

CRLC-RRC-MessageSN-REQ ::= SEQUENCE
{
  cellId INTEGER (-1..63),
  routingInfo RoutingInfo
}

--**************************************************************
--
-- CRLC-Resume-CNF
--   To confirm the resume request
--
--**************************************************************

CRLC-Resume-CNF ::= SEQUENCE {
  cellId INTEGER (-1..63),
  routingInfo RoutingInfo
}

--**************************************************************
--
-- CRLC-Resume-REQ
--   To request to resume data transmission.
--   If the SS implemented the optional suspension of UL data PDUs, then the processing in the UL of data PDUs shall be resumed. Any suspended UL control PDUs and Piggybacked Status shall be preceeded or resumed.
--
--**************************************************************

CRLC-Resume-REQ ::= SEQUENCE {
  cellId INTEGER (-1..63),
  routingInfo RoutingInfo
}

--**************************************************************
--
-- CRLC-SecurityMode-Config-CNF
--   To confirm to configure the ciphering
--
--**************************************************************

CRLC-SecurityMode-Config-CNF ::= SEQUENCE {
  cellId INTEGER (-1..63)
}

--**************************************************************
--
-- CRLC-SecurityMode-Config-REQ
--   To request to configure the RLC security mode
--   If several subsequent CRLC-Integrity-Activate-REQ or CRLC-Ciphering-Activate-REQ follow this ASP, the SS shall take a serial of specified actions on the same contents in this ASP at the activation time indicated in each CRLC- Integrity (or Ciphering)-Activate-REQ.
--
--**************************************************************

CRLC-SecurityMode-Config-REQ ::= SEQUENCE {
  cellId INTEGER (-1..63),
  rlcSecurityInfo SecurityInfo
}

--**************************************************************
--
-- CRLC-SequenceNumber-CNF
--   To return the requested counter sequence number to which the next DL PDU to be sent or the expected UL PDU to be received.
--
--**************************************************************

CRLC-SequenceNumber-CNF ::= SEQUENCE {
  cellId INTEGER (-1..63),
  routingInfo RoutingInfo,
  count-C-MSB-UL COUNT-C-MSB ,
  count-C-LSB-UL RLC-SequenceNumber,
  count-C-MSB-DL COUNT-C-MSB ,
  count-C-LSB-DL RLC-SequenceNumber
}

--**************************************************************
--
-- CRLC-SequenceNumber-REQ
--   To request the RLC layer to return current counter sequence numbers to which the next DL PDU to be sent or the expected UL PDU to be received.
--
--**************************************************************

CRLC-SequenceNumber-REQ ::= SEQUENCE {
  cellId INTEGER (-1..63),
  routingInfo RoutingInfo
}

--**************************************************************
--
-- CRLC-SetRRC-MessageSN-CNF
--   To confirm the RRC message sequence number setting request
--
--**************************************************************

CRLC-SetRRC-MessageSN-CNF ::= SEQUENCE
{
  cellId INTEGER (-1..63),
  routingInfo RoutingInfo
}

--**************************************************************
--
-- CRLC-SetRRC-MessageSN-REQ
--   To request the SS to set the RRC message sequence number in COUNT-I to the value specified in this ASP. The ASP is used to initialise SS RRC
--
--**************************************************************

CRLC-SetRRC-MessageSN-REQ ::= SEQUENCE
{
  cellId INTEGER (-1..63),
  routingInfo RoutingInfo,
  count-I-LSB-UL RRC-SequenceNumber OPTIONAL,
  count-I-LSB-DL RRC-SequenceNumber OPTIONAL
}

--**************************************************************
--
-- CRLC-Suspend-CNF
--   To confirm the suspension of data transmission. The parameter vt indicates either the value of the Send State Variable VT(S) for AM, or the value of Data State Varialble VT(US) for UM.
--
--**************************************************************

CRLC-Suspend-CNF ::= SEQUENCE {
  cellId INTEGER (-1..63),
  routingInfo RoutingInfo,
  vt RLC-SequenceNumber
}

--**************************************************************
--
-- CRLC-Suspend-REQ
--   To request the suspension of data transmission. The parameter n indicates that an RLC entity will not send a PDU with "Sequence Number" VT(S)+N for AM and "Sequence Number" VT(US)+N for UM, where N is a non-negative integer. Optionally an SS may start immediate suspension of processing of data PDUs in the UL. The UL control PDUs and Piggybacked Status may optionally be processed.
--
--**************************************************************

CRLC-Suspend-REQ ::= SEQUENCE {
  cellId INTEGER (-1..63),
  routingInfo RoutingInfo,
  n RLC-SequenceNumber
}

--**************************************************************
--
-- RLC-AM-DATA-CNF
--
--**************************************************************

RLC-AM-DATA-CNF ::= SEQUENCE {
  cellId INTEGER (-1..63),
  routingInfo RoutingInfo,
  mui Mui
}

--**************************************************************
--
-- RLC-AM-DATA-IND
--   To indicate to receive DATA using ackowledged mode
--
--**************************************************************

RLC-AM-DATA-IND ::= SEQUENCE {
  cellId INTEGER (-1..63),
  routingInfo RoutingInfo,
  integrityResult IntegrityResult ,
  aM-message CHOICE {
    uL-DCCH-Message UL-DCCH-Message,
    uL-CCCH-Message UL-CCCH-Message,
    uL-SHCCH-Message UL-SHCCH-Message
  }
}

--**************************************************************
--
-- RLC-AM-DATA-REQ
--   To request to transmit DATA using ackowledged mode
--
--**************************************************************

RLC-AM-DATA-REQ ::= SEQUENCE {
  cellId INTEGER (-1..63),
  routingInfo RoutingInfo,
  confirmationRequest AmConfirmationRequest,
  aM-message CHOICE {
    dL-DCCH-Message DL-DCCH-Message,
    dL-CCCH-Message DL-CCCH-Message,
    pCCH-Message PCCH-Message,
    dL-SHCCH-Message DL-SHCCH-Message,
    bCCH-FACH-Message BCCH-FACH-Message,
    bCCH-BCH-Message BCCH-BCH-Message,
    invalid-dL-DCCH-Message Invalid-DL-DCCH-Message 
    -- invalid-dL-CCCH-Message Invalid-DL-CCCH-Message,
    -- invalid-dL-SHCCH-Message Invalid-DL-SHCCH-Message
  }
}

--**************************************************************
--
-- RLC-TR-DATA-IND
--   To indicate to receivet DATA using transparent mode
--
--**************************************************************

RLC-TR-DATA-IND ::= SEQUENCE {
  cellId INTEGER (-1..63),
  routingInfo RoutingInfo,
  tM-message CHOICE {
    uL-DCCH-Message UL-DCCH-Message,
    uL-CCCH-Message UL-CCCH-Message,
    uL-SHCCH-Message UL-SHCCH-Message
  }
}

--**************************************************************
--
-- RLC-TR-DATA-REQ
--   To request to transmit DATA using transparent mode
--
--**************************************************************

RLC-TR-DATA-REQ ::= SEQUENCE {
  cellId INTEGER (-1..63),
  routingInfo RoutingInfo,
  tM-message CHOICE {
    dL-DCCH-Message DL-DCCH-Message,
    dL-CCCH-Message DL-CCCH-Message,
    pCCH-Message PCCH-Message,
    dL-SHCCH-Message DL-SHCCH-Message,
    bCCH-FACH-Message BCCH-FACH-Message,
    bCCH-BCH-Message BCCH-BCH-Message
    -- invalid-dL-DCCH-Message Invalid-DL-DCCH-Message,
    -- invalid-dL-CCCH-Message Invalid-DL-CCCH-Message,
    -- invalid-dL-SHCCH-Message Invalid-DL-SHCCH-Message
  }
}

--**************************************************************
--
-- RLC-UM-DATA-IND
--   To indicate to receivet DATA using unacknowledged mode
--
--**************************************************************

RLC-UM-DATA-IND ::= SEQUENCE {
  cellId INTEGER (-1..63),
  routingInfo RoutingInfo,
  integrityResult IntegrityResult,
  uM-message CHOICE {
    uL-DCCH-Message UL-DCCH-Message,
    uL-CCCH-Message UL-CCCH-Message,
    uL-SHCCH-Message UL-SHCCH-Message
  }
}

--**************************************************************
--
-- RLC-UM-DATA-REQ
--   To request to transmit DATA using unacknowledged mode
--
--**************************************************************

RLC-UM-DATA-REQ ::= SEQUENCE {
  cellId INTEGER (-1..63),
  routingInfo RoutingInfo,
  uM-message CHOICE {
    dL-DCCH-Message DL-DCCH-Message,
    dL-CCCH-Message DL-CCCH-Message,
    pCCH-Message PCCH-Message,
    dL-SHCCH-Message DL-SHCCH-Message,
    bCCH-FACH-Message BCCH-FACH-Message,
    bCCH-BCH-Message BCCH-BCH-Message,
    invalid-dL-DCCH-Message Invalid-DL-DCCH-Message --,
    -- invalid-dL-CCCH-Message Invalid-DL-CCCH-Message,
    -- invalid-dL-SHCCH-Message Invalid-DL-SHCCH-Message
  },
  specialLI BOOLEAN
}

--**************************************************************
--
-- CMAC-MACe-Config-CNF
--   Confirm a previous CMAC-MACe-Config-REQ being successful.
--
--**************************************************************

CMAC-MACe-Config-CNF ::= SEQUENCE {
  nodeB-Id INTEGER(0..63)
}

--**************************************************************
--
-- CMAC-MACe-Config-FDD-REQ
--
--**************************************************************

CMAC-MACe-Config-FDD-REQ ::= SEQUENCE {
  nodeB-Id INTEGER(0..63),
  configMessage CHOICE {
    setup MACeConfig,
    reconfig MACeConfig,
    reset NULL,
    release SS-ActivationTime
  }
}

--**************************************************************
--
-- CMAC-MACe-Config-TDD-REQ
--   PCO Type: CSAP
--
--**************************************************************

CMAC-MACe-Config-TDD-REQ ::= SEQUENCE {
  nodeB-Id INTEGER(0..63),
  configMessage CHOICE {
    setup MACeConfig-TDD,
    reconfig MACeConfig-TDD,
    reset NULL,
    release SS-ActivationTime
  }
}

--**************************************************************
--
-- CMAC-MACe-NodeB-CellMapping-CNF
--   Confirm a previous CMAC-MACe-NodeB-CellMapping-REQ being successful.
--
--**************************************************************

CMAC-MACe-NodeB-CellMapping-CNF ::= SEQUENCE {
  nodeB-Id INTEGER(0..63)
}

--**************************************************************
--
-- CMAC-MACe-NodeB-CellMapping-REQ
--   To put a set of cells under the control of a MAC-e entity indicated by nodeB-Id, which is configured by CMAC-MAC-e-Config-REQ.
--   This ASP establishes the routing relation between E-DCH related channels in these cells with a MAC-e entity.
--   A cell is mapped to only one NodeB, and the cellId allocation is unique in a test.
--
--**************************************************************

CMAC-MACe-NodeB-CellMapping-REQ ::= SEQUENCE    {
  nodeB-Id INTEGER(0..63),
  celllist SEQUENCE OF INTEGER (0..63)
}

--**************************************************************
--
-- CMAC-MACes-Config-CNF
--   Confirm a previous CMAC-MACes-Config-REQ being successful. cellId=-1.
--
--**************************************************************

CMAC-MACes-Config-CNF ::= SEQUENCE {
  cellId INTEGER (-1..63)
}

--**************************************************************
--
-- CMAC-MACes-Config-REQ
--   This ASP is used for creating and configuring, reconfiguring, resetting or releasing an MAC-es, a cell / nodeB-independent entity in the SS. cellId=-1.
--
--**************************************************************

CMAC-MACes-Config-REQ ::= SEQUENCE {
  cellId INTEGER (-1..63),
  configMessage CHOICE {
    setup MACesConfig,
    reconfig MACesConfig,
    reset NULL,
    release SS-ActivationTime }
}

--**************************************************************
--
-- CMAC-MAChs-TFRCconfigure-CNF
--   Applicable Rel-5 or later.
--   Confirm a previous CMAC-MAChs-TFRCconfigure-REQ being successful.
--
--**************************************************************

CMAC-MAChs-MACehs-TFRCconfigure-CNF ::= SEQUENCE {
  cellId INTEGER (-1..63)
}

--**************************************************************
--
-- CMAC-MAChs-TFRCconfigure-FDD-REQ
--   Applicable Rel-5 or later.
--   To configure the TFRC selection entity in the MAC-hs entity.
--   channelisationCodeOffset + noOfChannelisationCodes shall not be great than 15;
--   noOfChannelisaionCodes = 0 means to delete the HS-PDSCH and HS-SCCH channels, and release all related resource.
--   If explicit is selected, the SS shall use the values specified here for the parameters "modulationScheme", "channelisationCodeOffset", "noOfChannelisatonCodes ", tbSizeIndexOnHS-SCCH", "redundancyVersion" and "hs-PDSCH-TxPower".
--   If sS-Configured is selected, the values specified here are the ranges for  "channelisationCodeOffset", "noOfChannelisationCodes", and the initial value of HS-PDSCH transmission power, the SS shall dynamically select the suitable values for the parameters "modulationScheme", "channelisationCodeOffset", "noOfChannelisatonCodes ", tbSizeIndexOnHS-SCCH", "redundancyVersion"  and "hs-PDSCH-TxPower" according to the CQI information reported by the UE and the UE's capability category,
--
--**************************************************************

CMAC-MAChs-MACehs-TFRCconfigure-FDD-REQ ::= SEQUENCE {
  cellId INTEGER (-1..63),
  tfrcConfigMode CHOICE {
    explicitlyConfigured SEQUENCE {
      modulationScheme ModulationScheme,
      channelisationCodeOffset INTEGER (1..15), --@sic R5w140013 sic@
      noOfChannelisationCodes INTEGER (1..15),
      tbSizeIndexOnHS-SCCH INTEGER (0..63),
      minimumInterTTIinterval INTEGER (1..3),
      redundancyVersions RedundancyVersionList,
      hs-PDSCH-TxPower DL-TxPower -- default offset related
      -- to p-CPICH or s-CPICH
    },
    sS-Configured SEQUENCE {
      minChannelisationCodeOffset INTEGER (1..15),
      maxNoOfChannelisationCodes INTEGER (1..15),
      iniHS-PDSCH-TxPower DL-TxPower, -- default offset related
      -- to p-CPICH or s-CPICH
      hs-scch-LessInfo HS-SCCH-LessInfo-r7 OPTIONAL,
      mimoStatus BOOLEAN DEFAULT FALSE
    },
    explicitHS-SCCH-LessMode SEQUENCE{
      hs-pdsch-CodeIndex INTEGER (1..15),
      hs-scch-LessTFI INTEGER (1..90),
      hs-scch-LessSecondCodeApplicability BOOLEAN,
      tbs INTEGER (0..3),
      -- the index of tbs for HS-SCCH less operation
      -- The value should be consistent with code index, TFI and second
      -- code applicability
      minimumInterTTIinterval   INTEGER (1..3), 
      hs-PDSCH-TxPower DL-TxPower
      -- default offset related to p-CPICH or s-CPICH
    },
    explicitMIMO SEQUENCE {
      modulationSchemeAndNumTB INTEGER(0..7),
      -- set according to table 14 of 25.212
      -- Values 1,2 and 5 are used for 64QAM+MIMO. Rel-8 or later
      channelisationCodeOffset INTEGER (1..15),
      noOfChannelisationCodes INTEGER (1..15),
      precodingWeight2 INTEGER (0..3),
      -- set according to table 14a of 25.212
      primaryTB-SizeIndexOnHS-SCCH INTEGER (0..63),
      secondaryTB-SizeIndexOnHS-SCCH INTEGER (0..63) OPTIONAL,
      -- present only if second TB is to be tx as per modulationSchemeAndNumTB
      minimumInterTTIinterval INTEGER (1..3),
      primaryRedundancyVersions RedundancyVersionList,
      secondaryRedundancyVersions RedundancyVersionList OPTIONAL,
      -- present only if second TB is to be tx as per modulationSchemeAndNumTB
      hs-PDSCH-TxPower DL-TxPower -- default offset related
      -- to p-CPICH or s-CPICH
    },
    sS-Configured-DC SEQUENCE {
      serving-minChannelisationCodeOffset INTEGER (1..15),
      serving-maxNoOfChannelisationCodes INTEGER (1..15),
      serving-mimoStatus    BOOLEAN	DEFAULT FALSE,	-- Rel-9 or later
      sec-minChannelisationCodeOffset INTEGER (1..15),
      sec-maxNoOfChannelisationCodes INTEGER (1..15),
      sec-mimoStatus    BOOLEAN	DEFAULT FALSE,	-- Rel-9 or later
      iniHS-PDSCH-TxPower DL-TxPower,
      -- default offset related
      -- to p-CPICH or s-CPICH
      hs-scch-LessInfo HS-SCCH-LessInfo-r7	OPTIONAL
    },
    explicitlyDC SEQUENCE {
      servingTFRC SEQUENCE {
        modulationScheme ModulationScheme,
        channelisationCodeOffset INTEGER (1..15),
        noOfChannelisationCodes INTEGER (1..15),
        tbSizeIndexOnHS-SCCH INTEGER (0..63),
        minimumInterTTIinterval INTEGER (1..3),
        redundancyVersions RedundancyVersionList,
        hs-PDSCH-TxPower DL-TxPower	-- default offset related
        -- to p-CPICH or s-CPICH
      } OPTIONAL, -- when omitted then no data is sent on the serving HS-DSCH cell
      secondaryTFRC SEQUENCE {
        modulationScheme ModulationScheme,
        channelisationCodeOffset INTEGER (1..15),
        noOfChannelisationCodes INTEGER (1..15),
        tbSizeIndexOnHS-SCCH INTEGER (0..63),
        minimumInterTTIinterval INTEGER (1..3),
        redundancyVersions RedundancyVersionList,
        hs-PDSCH-TxPower DL-TxPower -- default offset related
        -- to p-CPICH or s-CPICH
      } OPTIONAL -- when omitted then no data is sent on the secondary HS-DSCH cell
    },
	explicitlyDC-MIMO		SEQUENCE {			-- Rel-9 or later 
		servingTFRC 	SEQUENCE{
			modulationSchemeAndNumTB			INTEGER(0..7),
				-- set according to table 14 of 25.212
				-- Values 1,2 and 5 are used for 64QAM+MIMO. Rel-8 or later
			channelisationCodeOffset			INTEGER (1..15),
			noOfChannelisationCodes				INTEGER (1..15),
			precodingWeight2					INTEGER (0..3),
				-- set according to table 14a of 25.212
			primaryTB-SizeIndexOnHS-SCCH		INTEGER (0..63),
			secondaryTB-SizeIndexOnHS-SCCH		INTEGER (0..63) OPTIONAL,
				-- present only if second TB is to be tx
				-- as per modulationSchemeAndNumTB
			minimumInterTTIinterval				INTEGER (1..3),
			primaryRedundancyVersions			RedundancyVersionList,
			secondaryRedundancyVersions			RedundancyVersionList OPTIONAL,
				-- present only if second TB is to be tx 
				-- as per modulationSchemeAndNumTB
			hs-PDSCH-TxPower					DL-TxPower	
				-- default offset related
				-- to p-CPICH or s-CPICH
			} OPTIONAL,
			-- when omitted then no data is sent on the serving HS-DSCH cell
		secondaryTFRC 	SEQUENCE{
			modulationSchemeAndNumTB			INTEGER(0..7),
				-- set according to table 14 of 25.212
				-- Values 1,2 and 5 are used for 64QAM+MIMO. Rel-8 or later
			channelisationCodeOffset			INTEGER (1..15),
			noOfChannelisationCodes				INTEGER (1..15),
			precodingWeight2					INTEGER (0..3),
				-- set according to table 14a of 25.212
			primaryTB-SizeIndexOnHS-SCCH		INTEGER (0..63),
			secondaryTB-SizeIndexOnHS-SCCH		INTEGER (0..63) OPTIONAL,
				-- present only if second TB is to be tx
				-- as per modulationSchemeAndNumTB
			minimumInterTTIinterval				INTEGER (1..3),
			primaryRedundancyVersions			RedundancyVersionList,
			secondaryRedundancyVersions			RedundancyVersionList OPTIONAL,
				-- present only if second TB is to be tx 
				-- as per modulationSchemeAndNumTB
			hs-PDSCH-TxPower					DL-TxPower	
				-- default offset related
				-- to p-CPICH or s-CPICH
			} OPTIONAL
			-- when omitted then no data is sent on the secondary HS-DSCH cell
		},
	relAspTypeExtension	 	TFRCconfigure-r10OrLaterExtensionType -- Rel-10 or later @sic R5-130613 R5-134957 sic@
  },
  activationTime SS-ActivationTime,
  ss-DTX-Info DRX-Info OPTIONAL,
  hs-DSCH-TBSizeTable HS-DSCH-TBSizeTable OPTIONAL
}

--**************************************************************
--
-- TFRCconfigure-r10OrLaterExtensionType
-- Rel-10 or later
-- Extension to configure the TFRC selection in the MAC-ehs entity when 4C-HSDPA or Multiflow is configured.
--
--**************************************************************
TFRCconfigure-r10OrLaterExtensionType ::= CHOICE {
	rel10-AspExt CHOICE	{
		sS-Configured-4C		SEQUENCE { -- Rel-10 3C/4C HSDPA
			serving-TFRC		TFRC-Configured-Type,	
			firstSecondary-TFRC		TFRC-Configured-Type,
			secondSecondary-TFRC	TFRC-Configured-Type,
			thirdSecondary-TFRC		TFRC-Configured-Type OPTIONAL, 
									-- for the third secondary cell when configured
			iniHS-PDSCH-TxPower		DL-TxPower,
									-- default offset related
									-- to p-CPICH or s-CPICH
			hs-scch-LessInfo		HS-SCCH-LessInfo-r7	OPTIONAL
			},
		explicitlyConfigured-4C		SEQUENCE { -- Rel-10 3C/4C HSDPA
			serving-TFRC			TFRC-Explicit-Type	OPTIONAL,
 				-- when omitted then no data is sent on the serving HS-DSCH cell
			firstSecondary-TFRC		TFRC-Explicit-Type	OPTIONAL,
				-- when omitted then no data is sent on the secondary HS-DSCH cell
			secondSecondary-TFRC	TFRC-Explicit-Type	OPTIONAL,
				-- when omitted then no data is sent on the secondary HS-DSCH cell
			thirdSecondary-TFRC		TFRC-Explicit-Type	OPTIONAL
				-- for the third secondary cell when configured
				-- when omitted then no data is sent on the secondary HS-DSCH cell
			},
		explicitlyConfigured-4C-MIMO		SEQUENCE { -- Rel-10 3C/4C HSDPA
			serving-TFRC 			TFRC-ExplicitMIMO-Type OPTIONAL,
				-- when omitted then no data is sent on the serving HS-DSCH cell
			firstSecondary-TFRC		TFRC-ExplicitMIMO-Type	OPTIONAL,
				-- when omitted then no data is sent on the secondary HS-DSCH cell
			secondSecondary-TFRC	TFRC-ExplicitMIMO-Type	OPTIONAL,
				-- when omitted then no data is sent on the secondary HS-DSCH cell
			thirdSecondary-TFRC		TFRC-ExplicitMIMO-Type	OPTIONAL
				-- for the third secondary cell when configured
				-- when omitted then no data is sent on the secondary HS-DSCH cell
			}
	},
	rel11-AspExt CHOICE	{ --@sic R5-145142 sic@
		sS-Configured-MF		SEQUENCE { -- Rel-11 Multiflow HSDPA
			nodeB-Id				INTEGER(0..63),
			serving-TFRC			TFRC-Configured-Type OPTIONAL,
				-- serving HS-DSCH cell
			assistingServing-TFRC	TFRC-Configured-Type OPTIONAL,
				-- assisting serving HS-DSCH cell
			secondary-TFRC			TFRC-Configured-Type OPTIONAL,
				-- secondary serving HS-DSCH cell
			assistingSecondary-TFRC	TFRC-Configured-Type OPTIONAL,
				-- assisting secondary serving HS-DSCH cell
			iniHS-PDSCH-TxPower		DL-TxPower
				-- default offset related
				-- to p-CPICH or s-CPICH
		},
		explicitlyConfigured-MF		SEQUENCE { -- Rel-11 Multiflow HSDPA
			nodeB-Id				INTEGER(0..63),
			serving-TFRC			TFRC-Explicit-Type	OPTIONAL,
				-- when omitted then no data is sent on the serving HS-DSCH cell
			assistingServing-TFRC	TFRC-Explicit-Type	OPTIONAL,
				-- when omitted then no data is sent on the assisting serving 
				-- HS-DSCH cell
			secondary-TFRC 			TFRC-Explicit-Type	OPTIONAL,
				-- when omitted then no data is sent on the secondary serving 
				-- HS-DSCH cell
			assistingSecondary-TFRC	TFRC-Explicit-Type	OPTIONAL
				-- when omitted then no data is sent on the assisting secondary
				-- serving HS-DSCH cell
			}
	}
}

--**************************************************************
--
-- TFRC-Configured-Type
-- Rel-10 or later.
--
--**************************************************************

TFRC-Configured-Type ::= SEQUENCE {
	minChannelisationCodeOffset	INTEGER (1..15),
	maxNoOfChannelisationCodes	INTEGER (1..15),
	mimoStatus					BOOLEAN	DEFAULT FALSE
}

--**************************************************************
--
-- TFRC-Explicit-Type
-- Rel-10 or later.
--
--**************************************************************

TFRC-Explicit-Type ::= SEQUENCE{
	modulationScheme				ModulationScheme,
	channelisationCodeOffset		INTEGER (1..15),
	noOfChannelisationCodes			INTEGER (1..15),
	tbSizeIndexOnHS-SCCH			INTEGER (0..63),
	minimumInterTTIinterval			INTEGER (1..3),
	redundancyVersions				RedundancyVersionList,
	hs-PDSCH-TxPower				DL-TxPower	-- default offset related
												-- to p-CPICH or s-CPICH
}

--**************************************************************
--
-- TFRC-ExplicitMIMO-Type
-- Rel-10 or later.
--
--**************************************************************

TFRC-ExplicitMIMO-Type ::= SEQUENCE{
	modulationSchemeAndNumTB			INTEGER(0..7),
		-- set according to table 14 of 25.212
		-- Values 1,2 and 5 are used for 64QAM+MIMO
	channelisationCodeOffset			INTEGER (1..15),
	noOfChannelisationCodes				INTEGER (1..15),
	precodingWeight2					INTEGER (0..3),
		-- set according to table 14a of 25.212
	primaryTB-SizeIndexOnHS-SCCH		INTEGER (0..63),
	secondaryTB-SizeIndexOnHS-SCCH		INTEGER (0..63) OPTIONAL,
		-- present only if second TB is to be tx
		-- as per modulationSchemeAndNumTB
	minimumInterTTIinterval				INTEGER (1..3),
	primaryRedundancyVersions			RedundancyVersionList,
	secondaryRedundancyVersions			RedundancyVersionList OPTIONAL,
		-- present only if second TB is to be tx 
		-- as per modulationSchemeAndNumTB
	hs-PDSCH-TxPower					DL-TxPower	
		-- default offset related
		-- to p-CPICH or s-CPICH
}


--**************************************************************
--
-- CMAC-MAChs-MACehs-TFRCconfigure-TDD-REQ
--   Applicable Rel-5 or later.
--   To configure the TFRC selection entity in the MAC-hs entity.
--   channelisationCodeOffset + noOfChannelisationCodes shall not be great than 15;
--   noOfChannelisaionCodes = 0 means to delete the HS-PDSCH and HS-SCCH channels, and release all related resource.
--   If explicit is selected, the SS shall use the values specified here for the parameters "modulationScheme", "channelisationCodeOffset", "noOfChannelisatonCodes ", tbSizeIndexOnHS-SCCH", "redundancyVersion" and "hs-PDSCH-TxPower".
--   If sS-Configured is selected, the values specified here are the ranges for  "channelisationCodeOffset", "noOfChannelisationCodes", and the initial value of HS-PDSCH transmission power, the SS shall dynamically select the suitable values for the parameters "modulationScheme", "channelisationCodeOffset", "noOfChannelisatonCodes ", tbSizeIndexOnHS-SCCH", "redundancyVersion"  and "hs-PDSCH-TxPower" according to the CQI information reported by the UE and the UE's capability category,
--
--**************************************************************

CMAC-MAChs-MACehs-TFRCconfigure-TDD-REQ ::= SEQUENCE {
  cellId INTEGER (-1..63),
  tfrcConfigMode CHOICE {
    explicitlyConfigured SEQUENCE {
      modulationScheme         ModulationScheme,
      noOfTimeSlots            BIT STRING (SIZE (5)),
      startCode         HS-ChannelisationCode-LCR,
      stopCode             HS-ChannelisationCode-LCR,
      noOfCodesPerTimeslot        INTEGER (0..16),
      tbSizeIndexOnHS-SCCH        INTEGER (0..63),
      redundancyVersions     RedundancyVersionList,
      hs-PDSCH-TxPower         DL-TxPower -- default offset related
      -- to p-PCCPCH
    },
    sS-Configured SEQUENCE {
      numofTimeslots            INTEGER (0..6),
      startCode         HS-ChannelisationCode-LCR,
      stopCode             HS-ChannelisationCode-LCR,
      numofCodesPerTimeslot     INTEGER (0..16),
      iniHS-PDSCH-TxPower DL-TxPower, -- default offset related
      sps-Information-TDD128	SPS-Information-TDD128-r8	OPTIONAL
    },
    relAspTypeExtension 		SEQUENCE{} -- Rel-10 or later
  }, 
  activationTime				SS-ActivationTime	OPTIONAL
}

--**************************************************************
--
-- HS-DPCCHInfo-r8
-- mimoStatus represents status of MIMO and shall be set only if mimo-Parameters are provided in HS-PDSCH configuration.
-- secondaryServing-HS-DSCH-Cell indicates if the HS-DSCH secondary serving cell is activated (see 3GPP TS 25.214[12] cl 6A.1)
-- @sic R5-101047 sic@
--
--**************************************************************

HS-DPCCHInfo-r8 ::= SEQUENCE {
  cqi-RepetitionFactor CQI-RepetitionFactor,
  ackNackRepetitionFactor ACK-NACK-repetitionFactor,
  mimoStatus BOOLEAN DEFAULT FALSE,
  secondaryServing-HS-DSCH-Cell ENUMERATED { deactivated (0), activated (1) } DEFAULT deactivated
  -- Rel-8 or later
}

--**************************************************************
--
-- SS-MBMS-MICHConfigurationInfo-r6
-- Rel-6 or later.
--
--**************************************************************

SS-MBMS-MICHConfigurationInfo-r6 ::= SEQUENCE {
  michinfo MBMS-MICHConfigurationInfo-r6,
  sccpchId-associated INTEGER (0..31)
}

--**************************************************************
--
-- Invalid-DL-DCCH-Message
--   PCO Type: DSAP
--
--**************************************************************

Invalid-DL-DCCH-Message ::= SEQUENCE {
  integrityCheckInfo [0] IntegrityCheckInfo OPTIONAL
--  asn1-message [1] Invalid-DL-DCCH-MsgType
}

U-CMAC-CONFIG-REQ ::= CHOICE {
      config-FDD CMAC-Config-FDD-REQ,
      config-TDD CMAC-Config-TDD-REQ,
      sysInfo CMAC-SYSINFO-Config-REQ,
      secMode CMAC-SecurityMode-Config-REQ,
      cipher CMAC-Ciphering-Activate-REQ,
      page-FDD CMAC-PAGING-Config-FDD-REQ,
      page-TDD CMAC-PAGING-Config-TDD-REQ,
      configMACes CMAC-MACes-Config-REQ,
      configMACe-FDD CMAC-MACe-Config-FDD-REQ,
      configMACe-TDD CMAC-MACe-Config-TDD-REQ,
      nodeB CMAC-MACe-NodeB-CellMapping-REQ,
      tfrc-FDD CMAC-MAChs-MACehs-TFRCconfigure-FDD-REQ,
      tfrc-TDD CMAC-MAChs-MACehs-TFRCconfigure-TDD-REQ,
	  configMACi-FDD  CMAC-MACi-Config-FDD-REQ,
	  configMACi-TDD  CMAC-MACi-Config-TDD-REQ,
	  nodeB-MACi  CMAC-MACi-NodeB-CellMapping-REQ,
	  configMACis   CMAC-MACis-Config-REQ,
	  configMACi-AG-FDD  CMAC-MACi-AG-FDD-REQ, --@sic R5w140013 sic@
	  configMACi-AG-TDD  CMAC-MACi-AG-TDD-REQ, --@sic R5w140013 sic@
	  configMACiE-TFC-FDD  CMAC-MACi-E-TFC-Restriction-FDD-REQ, --@sic R5w140208 sic@
	  configMACiE-TFC-TDD  CMAC-MACi-E-TFC-Restriction-TDD-REQ, --@sic R5w140208 sic@
	  configHARQ-MultiFlow CMAC-MACehs-HARQAssign-MultiFlows-REQ,
      configRestriction CMAC-Restriction-REQ,
      configMACehs-NodeB CMAC-ConfigMACehs-NodeB-REQ, -- @sic R5-145142 sic@
      mACehs-NodeB-CellMapping CMAC-MACehs-NodeB-CellMapping-REQ, -- @sic R5-145142 sic@
      mACehs-HARQAssign-NodeB CMAC-MACehs-HARQAssign-NodeB-REQ, -- @sic R5-145142 sic@
      fACH-Measurement-Occasions CMAC-FACH-MeasOccas-REQ  -- @sic R5s170587 sic@
}

U-CMAC-CONFIG-CNF ::= CHOICE {
      config CMAC-Config-CNF,
      sysInfo CMAC-SYSINFO-Config-CNF,
      secMode CMAC-SecurityMode-Config-CNF,
      cipher CMAC-Ciphering-Activate-CNF,
      page CMAC-PAGING-Config-CNF,
      configMACes CMAC-MACes-Config-CNF,
      configMACe CMAC-MACe-Config-CNF,
      nodeB CMAC-MACe-NodeB-CellMapping-CNF,
      tfrc CMAC-MAChs-MACehs-TFRCconfigure-CNF,
      configMACi CMAC-MACi-Config-CNF,
	  nodeB-MACi  CMAC-MACi-NodeB-CellMapping-CNF,
	  configMACis   CMAC-MACis-Config-CNF,
	  configMACi-AG-FDD  CMAC-MACi-AG-FDD-CNF,  -- @sic R5-144761 sic@
	  configMACi-AG-TDD  CMAC-MACi-AG-TDD-CNF,  -- @sic R5-144761 sic@
	  configMACiE-TFC  CMAC-MACi-E-TFC-Restriction-CNF ,
	  configHARQ-MultiFlow CMAC-MACehs-HARQAssign-MultiFlows-CNF,
      configRestriction CMAC-Restriction-CNF,
      configMACehs-NodeB CMAC-ConfigMACehs-NodeB-CNF, -- @sic R5-145142 sic@
      mACehs-NodeB-CellMapping CMAC-MACehs-NodeB-CellMapping-CNF, -- @sic R5-145142 sic@
      mACehs-HARQAssign-NodeB CMAC-MACehs-HARQAssign-NodeB-CNF, -- @sic R5-145142 sic@
      fACH-Measurement-Occasions CMAC-FACH-MeasOccas-CNF -- @sic R5s170587 sic@
}

U-CPHY-CONFIG-CNF ::= CHOICE {
      rlSetup CPHY-RL-Setup-CNF,
      rlModify CPHY-RL-Modify-CNF,
      rlRelease CPHY-RL-Release-CNF,
      trchConfig CPHY-TrCH-Config-CNF,
      trchRelease CPHY-TrCH-Release-CNF,
      cellConfig CPHY-Cell-Config-CNF,
      cellRelease CPHY-Cell-Release-CNF,
      ini CPHY-Ini-CNF,
      txPower CPHY-Cell-TxPower-Modify-CNF,
      frameNo CPHY-Frame-Number-CNF,
      sync CPHY-Sync-IND,
      outOfSync CPHY-Out-of-Sync-IND,
      hSDpcchCQI-MultiCell CPHY-HS-DPCCH-CQI-MultiCell-CNF,  -- @sic R5-134957 sic@
      hSDpcchCQI-MultiCellInd CPHY-HS-DPCCH-CQI-MultiCell-IND,  -- @sic R5-134957 sic@
      measurementConfig CPHY-MeasurementConfig-CNF,  -- @sic R5-134957 sic@
      hSDpcchCQI  CPHY-HS-DPCCH-CQI-CNF,
      hSDpcchCQI-Ind  CPHY-HS-DPCCH-CQI-IND,
	  prachMeasurementReport CPHY-PRACH-Measurement-Report-IND,	-- @sic R5-150125 feFACH sic@ 
	  prachMeasurement CPHY-PRACH-Measurement-CNF,	-- @sic R5-150125 feFACH sic@
	  cPHY-AICH-NegAckModeSet	CPHY-AICH-NegAckModeSet-CNF	-- @sic R5-150125 feFACH sic@
      }

U-CPHY-CONFIG-REQ ::= CHOICE {
      rlSetup-FDD CPHY-RL-Setup-FDD-REQ,
      rlSetup-TDD CPHY-RL-Setup-TDD-REQ,
      rlModify-FDD CPHY-RL-Modify-FDD-REQ,
      rlModify-TDD CPHY-RL-Modify-TDD-REQ,
      rlRelease-FDD CPHY-RL-Release-FDD-REQ,
      rlRelease-TDD CPHY-RL-Release-TDD-REQ,
      trchConfig-FDD CPHY-TrCH-Config-FDD-REQ,
      trchConfig-TDD CPHY-TrCH-Config-TDD-REQ,
      trchRelease-FDD CPHY-TrCH-Release-FDD-REQ,
      trchRelease-TDD CPHY-TrCH-Release-TDD-REQ,
      cellConfig-FDD CPHY-Cell-Config-FDD-REQ,
      cellConfig-TDD CPHY-Cell-Config-TDD-REQ,
      cellRelease CPHY-Cell-Release-REQ,
      ini CPHY-Ini-REQ,
      txPower CPHY-Cell-TxPower-Modify-REQ,
      frameNo CPHY-Frame-Number-REQ,
      hSDpcchCQI-MultiCell CPHY-HS-DPCCH-CQI-MultiCell-REQ,  -- @sic R5-134957 sic@
      measurementConfig CPHY-MeasurementConfig-REQ,  -- @sic R5-134957 sic@
      hSDpcchCQI  CPHY-HS-DPCCH-CQI-REQ,
	  prachMeasurement CPHY-PRACH-Measurement-REQ,	-- @sic R5-150125 feFACH sic@
	  cPHY-AICH-NegAckModeSet	CPHY-AICH-NegAckModeSet-REQ  -- @sic R5-150125 feFACH sic@
	}

U-CRLC-CONFIG-CNF ::= CHOICE {
      config CRLC-Config-CNF,
      seqNo CRLC-SequenceNumber-CNF,
      secMode CRLC-SecurityMode-Config-CNF,
      cipher CRLC-Ciphering-Activate-CNF,
      integrity CRLC-Integrity-Activate-CNF,
      integrityFail CRLC-Integrity-Failure-IND,
      setRRCmsgSN CRLC-SetRRC-MessageSN-CNF,
      rrcMsgSN CRLC-RRC-MessageSN-CNF,
      resume CRLC-Resume-CNF,
      suspend CRLC-Suspend-CNF,
      prohibit CRLC-ProhibitRLC-Ack-CNF,
	  bindTestDataMultiFlow CRLC-BindTestDataInMultipleMACehs-PDU-MultiFlows-CNF,
      bindTestDataMultiFlow-NodeB CRLC-BindTestDataInMultipleMACehs-PDU-NodeB-CNF  -- @sic R5-150124 MF sic@
}

U-CRLC-CONFIG-REQ ::= CHOICE {
      config-FDD CRLC-Config-FDD-REQ, -- @sic R5-110103 sic@
      config-TDD CRLC-Config-TDD-REQ, -- @sic R5-110103 sic@
      seqNo CRLC-SequenceNumber-REQ,
      secMode CRLC-SecurityMode-Config-REQ,
      cipher CRLC-Ciphering-Activate-REQ,
      integrity CRLC-Integrity-Activate-REQ,
      setRRCmsgSN CRLC-SetRRC-MessageSN-REQ,
      rrcMsgSN CRLC-RRC-MessageSN-REQ,
      resume CRLC-Resume-REQ,
      suspend CRLC-Suspend-REQ,
      prohibit CRLC-ProhibitRLC-Ack-REQ,
	  bindTestDataMultiFlow CRLC-BindTestDataInMultipleMACehs-PDU-MultiFlows-REQ,
      bindTestDataMultiFlow-NodeB CRLC-BindTestDataInMultipleMACehs-PDU-NodeB-REQ  -- @sic R5-150124 MF sic@
}

U-CPDCP-CONFIG-CNF ::= CHOICE {
      config CPDCP-Config-CNF
}

U-CPDCP-CONFIG-REQ ::= CHOICE {
      config CPDCP-Config-REQ
}
--**************************************************************
--
-- CMAC-MACi-Config-CNF
-- Rel-8 or later
-- Confirm a previous CMAC-MACi-Config-REQ being successful.
--
--**************************************************************
CMAC-MACi-Config-CNF ::= SEQUENCE {
  nodeB-Id	INTEGER(0..63)
}

--**************************************************************
--
-- CMAC-MACi-Config-FDD-REQ
-- Rel-8 or later
--
--**************************************************************
CMAC-MACi-Config-FDD-REQ ::= SEQUENCE	{
  nodeB-Id			INTEGER(0..63),
  configMessage		CHOICE	{
						setup		MACiConfig-FDD,
						reconfig	MACiConfig-FDD,
						reset		NULL,
						release		SS-ActivationTime
							}
}

--**************************************************************
--
-- CMAC-MACi-Config-TDD-REQ
-- Rel-8 or later
--
--**************************************************************
CMAC-MACi-Config-TDD-REQ ::= SEQUENCE	{
  nodeB-Id			INTEGER(0..63),
  configMessage		CHOICE	{
						setup		MACiConfig-TDD,
						reconfig	MACiConfig-TDD,
						reset		NULL,
						release		SS-ActivationTime
							}
}

--**************************************************************
--
-- MACiConfig-FDD
--  If the macHeaderManipulation field is 'NormalMacHeader' in lCH-Mappinglist, then data received on the E-DCH (MAC-i PDU) shall have it's MAC header inspected to de-multiplex and to determine the appropriate routing, and the MACis PDU shall be passed to the MAC-is together with the relevant LCH-ID, length, F, CFN and subframe number.
-- If the macHeaderManipulation field field is 'OmitMacHeader', then data received on the E-DCH (MAC-i PDU) shall have it's MAC header inspected to de-multiplex and to determine the appropriate routing, then the MAC-i layer shall deliver the MAC-is PDU, SI and the related  CFN, subframe number to the MAC-is entity.
-- connectedToMAC-is field is used to provide the possibility that the E DCH MACdFlows from only one MAC-i entity are connected to the MAC-is entity in the inter node B soft handover test cases. When MAC-i is configured in enhanced FACH UL using commonMac-i-r8, the MAC-i entity is always connected to MAC-is. In DC-HSUPA configuration, one MAC-i entity is connected to the MAC-is entity. In DC-HSUPA, e-DCHMacdFlows is applied to the two E-DCH transport channels in the primary and secondary UL frequency.
-- The IEs lCH-Mappinglist and e-DCHMacdFlows can be OMITted when changing the serving cell MAC-i without modification of MAC-i configurations. It will be applied in EDCH SHO.
-- ss-DRX-MAC-Info  presence indicates  UL DRX shall be applied.
-- Presence of tSN-FieldExtension indicates that the TSN field extension is used as defined in TS 25.321[17] clause 9.2.4.3; the absence indicates that 6 bits TSN is used.
--**************************************************************
MACiConfig-FDD ::= CHOICE	{
	mAC-i-r8	SEQUENCE {			-- Rel-8 or later
		activationTime		SS-ActivationTime,
		lCH-Mappinglist		LCH-MappingList		OPTIONAL,
		e-DCHMacdFlows		E-DCHMACdFlows		OPTIONAL,
		connectedToMAC-is	BOOLEAN DEFAULT TRUE, 
                            -- can be set to FALSE in inter nodeB SHO
		ss-DRX-MAC-Info		SS-DRX-MAC-Info		OPTIONAL
	},
	commonMac-i-r8	SEQUENCE	{
		activationTime		SS-ActivationTime,
		lCH-Mappinglist		LCH-MappingList				OPTIONAL,
		e-DCHMacdFlows		CommonE-DCHMACdFlows		OPTIONAL,
		additional-E-DCH-TransmitBackoff	INTEGER (0..15),
		max-CCCH-ResourceAllocation			ENUMERATED {
						tti8(0), tti12(1), tti16(2), tti20(3), tti24(4), tti32(5),
						tti40(6), tti80(7)},
		max-PeriodForCollisionResolution	INTEGER (8..24)
	},
    mAC-i-r9	SEQUENCE {			-- Rel-9 or later
		activationTime		SS-ActivationTime,
		lCH-Mappinglist		LCH-MappingList		OPTIONAL,
		e-DCHMacdFlows		E-DCHMACdFlows		OPTIONAL,
		connectedToMAC-is	BOOLEAN DEFAULT TRUE,  -- can be set to FALSE in inter nodeB SHO
		ss-DRX-MAC-Info		SS-DRX-MAC-Info		OPTIONAL,
		tSN-FieldExtension	BOOLEAN	DEFAULT FALSE
	},
    relAspTypeExtension SEQUENCE{} 	-- Rel-10 or later @sic R5-130613 sic@
}

--**************************************************************
--
-- MACiConfig-TDD
--  If the macHeaderManipulation field is 'NormalMacHeader' in lCH-Mappinglist, then data received on the E-DCH (MAC-i PDU) shall have it's MAC header inspected to de-multiplex and to determine the appropriate routing, and the MACis PDU shall be passed to the MAC-is together with the relevant LCH-ID, length, F, CFN and subframe number.
-- If the macHeaderManipulation field field is 'OmitMacHeader', then data received on the E-DCH (MAC-i PDU) shall have it's MAC header inspected to de-multiplex and to determine the appropriate routing, then the MAC-i layer shall deliver the MAC-is PDU, SI and the related  CFN, subframe number to the MAC-is entity.
-- connectedToMAC-is field is used to provide the possibility that the E DCH MACdFlows from only one MAC-i entity are connected to the MAC-is entity in the inter node B soft handover test cases. When MAC-i is configured in enhanced FACH UL using commonMac-i-r8, the MAC-i entity is always connected to MAC-is. In DC-HSUPA configuration, one MAC-i entity is connected to the MAC-is entity. In DC-HSUPA, e-DCHMacdFlows is applied to the two E-DCH transport channels in the primary and secondary UL frequency.
-- The IEs lCH-Mappinglist and e-DCHMacdFlows can be OMITted when changing the serving cell MAC-i without modification of MAC-i configurations. It will be applied in EDCH SHO.
-- ss-DRX-MAC-Info  presence indicates  UL DRX shall be applied.
--
--**************************************************************
MACiConfig-TDD ::= CHOICE	{
	mAC-i-r8	SEQUENCE {			-- Rel-8 or later
		activationTime		SS-ActivationTime,
		lCH-Mappinglist		LCH-MappingList		OPTIONAL,
		e-DCHMacdFlows		E-DCHMACdFlows-TDD		OPTIONAL,
		connectedToMAC-is	BOOLEAN DEFAULT TRUE
                            -- can be set to FALSE in inter nodeB SHO
	},
	commonMac-i-r8	SEQUENCE	{
		activationTime		SS-ActivationTime,
		lCH-Mappinglist		LCH-MappingList				OPTIONAL,
		e-DCHMacdFlows		CommonE-DCHMACdFlows		OPTIONAL  --@sic R5w140013 sic@
	},
    relAspTypeExtension SEQUENCE{} 	-- Rel-10 or later @sic R5-130613 sic@
}

--**************************************************************
--
-- CMAC-MACi-NodeB-CellMapping-CNF
-- Rel-8 or later
-- Confirm a previous CMAC-MACi-NodeB-CellMapping-REQ being successful.
-- 
--**************************************************************
CMAC-MACi-NodeB-CellMapping-CNF ::= SEQUENCE {
		nodeB-Id			INTEGER(0..63)
}

--**************************************************************
--
-- CMAC-MACi-NodeB-CellMapping-REQ
-- Rel-8 or later
-- To put a set of cells under the control of a MAC-i entity indicated by nodeB-Id, which is configured by CMAC-MAC-i-Config-REQ.
-- This ASP establishes the routing relation between E-DCH related channels in these cells with a MAC-i entity.
-- A cell is mapped to only one NodeB, and the cellId allocation is unique in a test.
-- 
--**************************************************************
CMAC-MACi-NodeB-CellMapping-REQ ::= SEQUENCE	{
	nodeB-Id			INTEGER(0..63),
	celllist			SEQUENCE OF INTEGER (0..63)
}

--**************************************************************
--
-- CMAC-MACis-Config-CNF
-- Rel-8 or later
-- Confirm a previous CMAC-MACis-Config-REQ being successful. cellId=-1 except when CCCH is configured to MAC-i is entity.
-- 
--**************************************************************
CMAC-MACis-Config-CNF ::= SEQUENCE {
		cellId				INTEGER(-1..63)
}

--**************************************************************
--
-- CMAC-MACis-Config-REQ
-- Rel-8 or later
-- This ASP is used for creating and configuring, reconfiguring, resetting or releasing an MAC-is, a cell / nodeB-independent entity in the SS, cellId=-1 except when CCCH is configured to MAC-i is entity.
--
--**************************************************************
CMAC-MACis-Config-REQ ::= SEQUENCE	{
		cellId				INTEGER(-1..63),
		configMessage		CHOICE	{
			setup				MACisConfig,
			reconfig			MACisConfig,
			reset				NULL,
			release				SS-ActivationTime}
}

--**************************************************************
--
-- MACisConfig
--  MACisConfig establishes the mapping between logical channels and E DCH-MACd-Flows.
--  When the macTestMode is TRUE, the re-ordering entity shall not eliminate the duplicated packets, but passes them to RLC. macTestMode = "TRUE" is used for testing the retransmission function of HARQ process.
--  Presence of tSN-FieldExtension indicates that the TSN field extension is used as defined in TS 25.321[17] clause 9.2.4.3; the absence indicates that 6 bits TSN is used.
--**************************************************************
MACisConfig ::= CHOICE	{
	mACis-r8	SEQUENCE	{							-- Rel-8 or later
			activationTime		SS-ActivationTime,
			lCHMappinglist		LCH-MappingList,
			macTestMode			BOOLEAN DEFAULT FALSE
	},
	mACis-r9	SEQUENCE	{							-- Rel-9 or later
			activationTime		SS-ActivationTime,
			lCHMappinglist		LCH-MappingList,
			macTestMode			BOOLEAN DEFAULT FALSE, 
			tSN-FieldExtension	BOOLEAN	DEFAULT FALSE
	},
	relAspTypeExtension	 		SEQUENCE{}	-- Rel-10 or later @sic r5-130613 sic@
}


--**************************************************************
--
-- LCH-MappingList
-- 
--**************************************************************
LCH-MappingList ::= SEQUENCE (SIZE (1..31)) OF LCH-Mapping


--**************************************************************
--
-- LCH-Mapping
-- Both SRBs and RBs can be mapped onto E-DCH. The mechanism for control of MAC header manipulation (macHeaderManipulation) is applied to individual logical channels to be mapped on E-DCH. Typically, the SRBs are configured in 'NormalMacHeader" mode while the RBs in user plane can be configured either in 'NormalMacHeader" or in "OmitMacHeader" mode.
-- If the value of macHeaderManipulation field is 'NormalMacHeader', then data received on the E-DCH MACd flows supporting this logical channel shall have its MAC header inspected to determine the appropriate routing, and removed as normal. The MACis SDU shall be passed to the appropriate logical channel.
-- If the value of macHeaderManipulation field is 'OmitMacHeader', then data received on the E-DCH MACd flows supporting this logical channel shall have it's MAC header inspected to determine the appropriate routing, then the MAC-is layer shall deliver the MAC-is SDU, LCH-ID, Length, F,SI and the related CFN, subframe number, HARQ process identity to the appropriate logical channel. The TTCN receives these fields by RLC-TR-MACis-DATA-IND, then these fields can be checked by the TTCN.
-- HARQ ID = CFN mod 4 for TTI=10ms;
-- HARQ ID = (5*CFN + subframe number) mod 8 for TTI=2ms
--
--**************************************************************
LCH-Mapping ::= SEQUENCE {
		macHeaderManipulation				MAC-HeaderManipulation,
		logicalChannelIdentity				LogicalChannelIdentity,
		e-DCH-MAC-d-FlowIdentity			E-DCH-MAC-d-FlowIdentity,
		rlc-PDU-Size	CHOICE	{
			flexibleSize	 					RLC-PDU-SizeConstraint,
			fixedSize							RLC-PDU-SizeList
		},
		includeInSchedulingInfo				BOOLEAN,
		mac-LogicalChannelPriority			MAC-LogicalChannelPriority,
		logicalChannelType					LogicalChannelType,
		rB-Identity							INTEGER	(-31..32)	OPTIONAL
}


--**************************************************************
--
-- CMAC-MACi-AG-FDD-CNF   @sic R5-144761 sic@
-- Confirm a previous CMAC-MACi-AG-REQ being successful.
--
--**************************************************************
CMAC-MACi-AG-FDD-CNF ::= SEQUENCE {
		nodeB-Id				INTEGER(0..63),
   		cellId					INTEGER(0..63)  -- @sic R5-134957 sic@
}

--**************************************************************
--
-- CMAC-MACi-AG-TDD-CNF   @sic R5-144761 sic@
-- Confirm a previous CMAC-MACi-AG-REQ being successful.
--
--**************************************************************
CMAC-MACi-AG-TDD-CNF ::= SEQUENCE { 
		nodeB-Id				INTEGER(0..63)
}

--**************************************************************
--
-- CMAC-MACi-AG-FDD-REQ
-- The hARQProcId shall be converted to the nearest CFN (and subframe number if TTI = 2 ms) by the SS, and the Absolute Grant is sent in that CFN (and subframe number if TTI = 2 ms). 
-- The absolute grant is applied on the A-GCH configured in the referred cellId.
-- 
--**************************************************************
CMAC-MACi-AG-FDD-REQ ::= SEQUENCE	{
			nodeB-Id			INTEGER(0..63),
            cellId				INTEGER(0..63),
			grantType			ENUMERATED {primary(0), secondary(1)},
			absoluteGrantValue	BIT STRING(SIZE(5)),
			absoluteGrantScope	BIT STRING(SIZE(1)),
			hARQProcId			INTEGER (0..7),
			activationTime		SS-ActivationTime
}

--**************************************************************
--
-- CMAC-MACi-AG-TDD-REQ
-- The hARQProcId shall be converted to the nearest CFN (and subframe number if TTI = 2 ms) by the SS, and the Absolute Grant is sent in that CFN (and subframe number if TTI = 2 ms). 
-- The absolute grant is applied on the A-GCH configured in the referred cellId.
-- 
--**************************************************************
CMAC-MACi-AG-TDD-REQ ::= SEQUENCE	{
    nodeB-Id                INTEGER(0..63),
    absoluteGrantValue      BIT STRING(SIZE(5)),
    channelisationCode      UL-TS-ChannelisationCode,
    tRRI                    BIT STRING(SIZE(5)),
    rDI                     INTEGER(0..7),
    eCSN                    INTEGER(0..7),
    eI                      INTEGER(0..3),
    eNI                     INTEGER(0..7),
    hARQProcId              INTEGER (0..7),
    activationTime          SS-ActivationTime        
}

--**************************************************************
--
-- CMAC-MACi-E-TFC-Restriction-CNF
-- Rel-8 or later
-- For MAC emulator to report that a previous attempt of restricting TFCs have been successful
--
--**************************************************************
CMAC-MACi-E-TFC-Restriction-CNF ::= SEQUENCE	{
			nodeB-Id			INTEGER(0..63),
			cellId				INTEGER(0..63)  -- @sic R5-134957 sic@
}


--**************************************************************
--
-- CMAC-MACi-E-TFC-Restriction-FDD-REQ
-- Rel-8 or later
-- To request to configure MACi entity. The field restrictAllowedTFCs is provided to allow the E-TFCI to be restricted on the referred cell Id. The IE fullE-TFCS will be used to remove any previous E-TFCS restriction configured.
--
--**************************************************************
CMAC-MACi-E-TFC-Restriction-FDD-REQ ::= SEQUENCE {
		nodeB-Id			INTEGER (0..63),
        cellId				INTEGER(0..63),  -- @sic R5-134957 sic@
		restrictAllowedTFCs	CHOICE {
								e-TFCS-Restriction		E-TFCS-Restriction,
								fullE-TFCS				NULL }
}

--**************************************************************
--
-- CMAC-MACi-E-TFC-Restriction-TDD-REQ
-- Rel-8 or later
-- To request to configure MACi entity. The field restrictAllowedTFCs is provided to allow the E-TFCI to be restricted on the referred cell Id. The IE fullE-TFCS will be used to remove any previous E-TFCS restriction configured.
--
--**************************************************************
CMAC-MACi-E-TFC-Restriction-TDD-REQ ::= SEQUENCE {
    nodeB-Id	INTEGER (0..63),
    cellId		INTEGER(0..63),  -- @sic R5-134957 sic@
    restrictAllowedTFCs	CHOICE {
        e-TFCS-Restriction	E-TFCS-Restriction-TDD,
        fullE-TFCS		NULL 
    }
}

E-TFCS-Restriction-TDD ::= SEQUENCE OF INTEGER (0..63)


--**************************************************************
--
-- E-TFCS-Restriction
-- The E-TFCS restriction is a list of E-TFCIs, and can be used to verify that the UE has used a specific TFC. Any data received by the SS using a forbidden TFCI shall be discarded.
--
--**************************************************************
E-TFCS-Restriction ::= SEQUENCE OF INTEGER (0..127)


--**************************************************************
--
-- CMAC-MACehs-HARQAssign-MultiFlows-CNF
-- Applicable Rel-7 or later
-- Confirm a previous CMAC-MACehs-HARQAssign-MultiFlows-REQ being successful.
--
--**************************************************************
CMAC-MACehs-HARQAssign-MultiFlows-CNF ::= SEQUENCE {
		cellId				INTEGER(-1..63)
}

--**************************************************************
--
-- CMAC-MACehs-HARQAssign-MultiFlows-REQ
-- Applicable Rel-7 or later
-- To assign the HARQ processes for the simultaneous transmission of the MAC-ehs PDUs on the different flows on the same TTI .
-- After successful transmission the MAC-ehs returns back to normal operation. In the normal operation suitable HARQ processes are selected by HARQ entities in the MAC-ehs to serve the MAC-ehs PDU without TTCN intervening.
-- For Dual Cell, the primaryFlow corresponds to the serving cell, the secPrimaryFlow corresponds to the secondary cell.
-- For MIMO, the primary and secondary HARQ process identities (of serving cell) are set as per 3GPP TS 25.212 [58], subclause 4.6B.2.5.
-- For combined DC-HSDPA and MIMO the primaryFlow and secondary flow correspond to the serving cell, the secPrimaryFlow and secSecondaryFlow to the secondary cell.
--
--**************************************************************
CMAC-MACehs-HARQAssign-MultiFlows-REQ ::= SEQUENCE	{
	cellId							INTEGER(-1..63),
	primaryFlowHarqProcessId		INTEGER(0..15|31),  			-- of serving cell
	secondaryFlowHarqProcessId		INTEGER(0..15|31) 	OPTIONAL,	-- of serving cell
	secPrimaryFlowHarqProcessId		INTEGER(0..15|31)	OPTIONAL,
									-- of secondary cell	Rel-9 or later
	secSecondaryFlowHarqProcessId	INTEGER(0..15|31)	OPTIONAL,
									-- of secondary cell	Rel-9 or later
	relAspTypeExtension	 			HARQAssign-MultiFlows-r10OrLaterExtensionType OPTIONAL -- Rel-10 or later @sic R5-130613 R5-134957 sic@
}

--**************************************************************
--
-- CMAC-MACehs-HARQAssign-MultiFlows-REQ
-- Rel-10 or later
-- Extension to assign the HARQ processes for the simultaneous transmission of the MAC-ehs PDUs on the different flows on the second and third secondary cells on the same TTI when 4C-HSDPA is configured.
-- In 4C-HSDPA, the primaryFlow corresponds to the serving cell, the secPrimaryFlow corresponds to the first secondary cell, the thirdPrimaryFlow corresponds to the second secondary cell, the fourthPrimaryFlow corresponds to the third secondary cell, when configured.
-- In 4C-HSDPA and MIMO: the primaryFlow and secondaryFlow corresponds to the serving cell. The secPrimaryFlow and secSecondaryFlow corresponds to the first secondary cell. The thirdPrimaryFlow and thirdSecondaryFlow corresponds to the second secondary cell. The fourthPrimaryFlow and fourthSecondaryFlow corresponds to the third secondary cell, when configured.
--
--**************************************************************

HARQAssign-MultiFlows-r10OrLaterExtensionType ::= CHOICE {
	rel10-AspExt	SEQUENCE	{
		thirdPrimaryFlowHarqProcessId		INTEGER(0..15|31),
  			-- of third cell
		thirdSecondaryFlowHarqProcessId		INTEGER(0..15|31) 	OPTIONAL,
			-- for MIMO in third cell
		fourthPrimaryFlowHarqProcessId		INTEGER(0..15|31)	OPTIONAL,
			-- of fourth cell for 4C-HSDPA
		fourthSecondaryFlowHarqProcessId	INTEGER(0..15|31)	OPTIONAL
			-- for MIMO in fourth cell for 4C-HSDPA
	}
}

--**************************************************************
--
-- CMAC-ConfigMACehs-NodeB-REQ
-- FDD rel-11 or later
-- To configure a MAC-ehs entity. 
--  - setup is used for creation of the MAC-ehs entity;
--  - release the MAC-ehs entity;
--  - reconfiguration is used to modify the MAC-ehs parameters.
--
--**************************************************************
CMAC-ConfigMACehs-NodeB-REQ ::= SEQUENCE	{
	nodeB-Id			INTEGER(0..63),
	routingInfo		RoutingInfo,
	ratType			RatType,
	activationTime	SS-ActivationTime,
	configMessage	CHOICE {
		setup			CmacConfigReq-r11OrLater,
		reconfigure		CmacConfigReq-r11OrLater,
		release			NULL
	}
}

CmacConfigReq-r11OrLater ::= CHOICE {
	rel11	SEQUENCE	{
		uE-Info								UE-Info,
		trCHInfo							TrCHInfo,
		trCH-LogCHMapping					TrCH-LogCHMappingList1,
		associatedPhychConfigToFollow		BOOLEAN DEFAULT FALSE,
		tSN-FieldExtension					BOOLEAN	DEFAULT FALSE
	}
}

--**************************************************************
--
-- CMAC-ConfigMACehs-NodeB-CNF
-- Confirm a previous CMAC-ConfigMACehs-NodeB-REQ successful.
--
--**************************************************************
CMAC-ConfigMACehs-NodeB-CNF ::= SEQUENCE {
	nodeB-Id			INTEGER(0..63)
}

--**************************************************************
--
-- CMAC-MACehs-NodeB-CellMapping-REQ
-- FDD rel-11 or later.
-- To put a set of cells under the control of a MAC-ehs entity indicated by nodeB-Id, which is configured by CMAC-ConfigMACehs-NodeB-REQ.
-- This ASP establishes the routing relation between HS-DSCH related channels in these cells with a MAC-ehs entity.
-- When a cell is mapped to the MAC-ehs entity then data can be transmitted on the HS-PDSCH of that cell. When a cell is unmapped then it is deactivated.
-- A cell is mapped to only one NodeB.
--
--**************************************************************
CMAC-MACehs-NodeB-CellMapping-REQ ::= SEQUENCE	{
	nodeB-Id		INTEGER(0..63),
    activationTime	SS-ActivationTime,          --@sic R5-150124 sic@
	cellList		SEQUENCE (SIZE (1..4)) OF MappingCellInfo-Type
}

MappingCellInfo-Type ::= SEQUENCE {
	cellId						INTEGER(0..63),
	multiflowCellConfiguration	MultiflowCellConfiguration-Type	OPTIONAL,
	timeReferenceCell			ENUMERATED { true }		OPTIONAL
}

MultiflowCellConfiguration-Type ::= ENUMERATED { serving, assistingServing, secondaryServing, assistingSecondaryServing }


--**************************************************************
--
-- CMAC-MACehs-NodeB-CellMapping-CNF
-- Confirm a previous CMAC-MACehs-NodeB-CellMapping-REQ being successful.
--
--**************************************************************
CMAC-MACehs-NodeB-CellMapping-CNF ::= SEQUENCE {
	nodeB-Id		INTEGER(0..63)
}

--**************************************************************
--
-- CMAC-MACehs-HARQAssign-NodeB-REQ
-- Applicable Rel-11 or later
-- To assign the HARQ processes for the simultaneous transmission of the MAC-ehs PDUs on the different flows in the same TTI (assisting serving and assisting secondary serving being shifted by cell timing offset).
-- After successful transmission the MAC-ehs entities return back to normal operation. In the normal operation suitable HARQ processes are selected by HARQ entities in the MAC-ehs to serve the MAC-ehs PDU without TTCN intervening.
--
--**************************************************************
CMAC-MACehs-HARQAssign-NodeB-REQ ::= SEQUENCE { 	
    harqFlowsPerNodeB	SEQUENCE (SIZE (1..2)) OF NodeB-HarqFlowList-Type
}

NodeB-HarqFlowList-Type ::= SEQUENCE {
	nodeB-Id								INTEGER(0..63),
	servingFlowHarqProcessId				INTEGER(0..15|31)	OPTIONAL,
	assistingServingFlowHarqProcessId		INTEGER(0..15|31)	OPTIONAL,	
	secondaryFlowHarqProcessId				INTEGER(0..15|31)	OPTIONAL,
	assistingSecondaryFlowHarqProcessId	INTEGER(0..15|31)	OPTIONAL
}

--**************************************************************
--
-- CMAC-MACehs-HARQAssign-NodeB-CNF
-- Applicable Rel-11 or later
-- Confirm a previous CMAC-MACehs-HARQAssign-NodeB-REQ being successful.
--
--**************************************************************
CMAC-MACehs-HARQAssign-NodeB-CNF ::= SEQUENCE {}

--**************************************************************
--
-- CMAC-Restriction-REQ
-- To request to configure MAC entity. The field restrictAllowedTFCs is provided to allow the UL and/or DL SS TFCS to be restricted for a specific transport channel. This information only needs to be sent to the MAC layer, since it is the MAC layer's responsibility to determine the set of valid TFCs each TTI.
--
--**************************************************************
CMAC-Restriction-REQ ::= SEQUENCE {
  cellId INTEGER (-1..63),
  routingInfo RoutingInfo,
  ratType RatType,
  restrictAllowedTFCs TFC-Restriction
}

--**************************************************************
-- TFC-Restriction
-- This type is used to specify the allowed TFCs within the current TFCS. A TFC restriction is applicable until a subsequent TFC restriction is applied. TFC restrictions are not cumulative, so each TFC restriction completely replaces the previous TFC restriction.The downlink restriction can be used to ensure that the SS uses a specific TFC for transmission of data, by only allowing the 'No data' TFC, and the 'desired' TFC. It may also be necessary to include one or more 'signalling only' TFCs to allow signalling to occur.The uplink restriction can be used to verify that the UE has used a specific TFC. Any data received by the SS using a forbidden TFCI shall be discarded.
--**************************************************************
TFC-Restriction ::= SEQUENCE {
  ulTFCI-Restriction TFC-Subset OPTIONAL,
  dlTFCI-Restriction TFC-Subset OPTIONAL
}

--**************************************************************
--
-- CMAC-Restriction-CNF
-- For MAC emulator to report that a previous attempt of restricting TFCs have been successful.
--
--**************************************************************
CMAC-Restriction-CNF ::= SEQUENCE {
  cellId INTEGER(-1..63),
  routingInfo RoutingInfo
}


--**************************************************************
--
-- CMAC-FACH-MeasOccas-REQ
-- To request MAC layer to configure FACH Measurement Occasions (FMO).
-- If IE "Inter-frequency FDD measurement indicator" is set to TRUE, the SS will start inter-frequency FMO handling at the activationTime. If this IE is set to FALSE, the SS inter-frequency FMO handling will be stopped at the activation Time.
-- For the FDD test, the IE "Inter-frequency TDD measurement indicator" is set to FALSE.
-- For GSM or LTE measurement, if IE "Inter-RAT measurement indicators" is included, independent of the RAT-Type, the SS will start inter-RAT FMO handling at the activationTime. If this IE is omitted, the SS inter-RAT FMO handling will be stopped at the activation Time.
-- 
-- largest_TTI_Number is the TTI (in number of 10ms frames) of the FACH having the largest TTI on the SCCPCH.
-- @sic R5-174639 sic@
--**************************************************************
CMAC-FACH-MeasOccas-REQ ::= SEQUENCE {
  cellId INTEGER (0..63),
  routingInfo RoutingInfo,
  fMO FACH-MeasurementOccasionInfo,
  largest-TTI INTEGER (1..8),
  activationTime	SS-ActivationTime  
}

--**************************************************************
--
-- CMAC-FACH-MeasOccas-CNF
-- To confirm to config FACH Measurement Occasions
--
--**************************************************************
CMAC-FACH-MeasOccas-CNF ::= SEQUENCE {
  cellId INTEGER (0..63),
  routingInfo RoutingInfo  
}

--**************************************************************
-- 
-- CRLC-BindTestDataInMultipleMACehs-PDU-MultiFlows-CNF
-- To confirm the request of binding subsequent data sending RLC-TR/UM/AM-TestDataReq on the specified RB mapped on HS-DSCH.
--
--**************************************************************
CRLC-BindTestDataInMultipleMACehs-PDU-MultiFlows-CNF ::= SEQUENCE{
	cellId			INTEGER(-1..63),
	routingInfo		RoutingInfo,			-- RB ID desired to be given
	result			ENUMERATED{failure(0), success(1)}
}

--**************************************************************
-- 
-- CRLC-BindTestDataInMultipleMACehs-PDU-MultiFlows-REQ
-- To request of binding subsequent data sending RLC-TR/UM/AM-TestDataReq on the specified RB mapped on HS-DSCH in two MAC-ehs PDUs, one for each primary and secondary flow.
-- On the request, the transmission of the test data is temporarily suppressed on the radio bearer till all SDUs for all flows are received by RLC layer on the Radio Bearer. After receiving all SDU's the RLC layer submits to MAC such that all of them are sent in two MAC-ehs PDUs.
--
--**************************************************************
CRLC-BindTestDataInMultipleMACehs-PDU-MultiFlows-REQ ::= SEQUENCE{
 	cellId						INTEGER(-1..63),
 	routingInfo					RoutingInfo,	-- RB ID desired to be given
 	primaryFlowNumOfSDUs		INTEGER,
		-- Number of RLC SDU's for primary flow of serving cell
	secondaryFlowNumOfSDUs		INTEGER 	OPTIONAL,
		-- Number of RLC SDU's for secondary flow of serving cell
	secPrimaryFlowNumOfSDUs		INTEGER		OPTIONAL,
		-- Number of RLC SDU's for secondary cell primary flow	Rel-9 or later
	secSecondaryFlowNumOfSDUs	INTEGER		OPTIONAL,
		-- Number of RLC SDU's for secondary cell secondary flow	Rel-9 or later
    relAspTypeExtension	 BindTestDataInMultipleMACehs-r10OrLaterExtensionType OPTIONAL	-- Rel-10 or later @sic R5-130613 R5-134957 sic@
}

--**************************************************************
-- 
-- BindTestDataInMultipleMACehs-r10OrLaterExtensionType
--
--**************************************************************
BindTestDataInMultipleMACehs-r10OrLaterExtensionType ::= CHOICE {
	rel10-AspExt SEQUENCE { -- Extension for 4C-HSDPA with or without MIMO 		
        thirdPrimaryFlowNumOfSDUs		INTEGER,
		-- Number of RLC SDU's for primary flow of third cell
		thirdSecondaryFlowNumOfSDUs		INTEGER 	OPTIONAL,
		-- Number of RLC SDU's for secondary flow of third cell
		fourthPrimaryFlowNumOfSDUs		INTEGER		OPTIONAL,
		-- Number of RLC SDU's for fourth cell primary flow
		fourthSecondaryFlowNumOfSDUs	INTEGER		OPTIONAL
		-- Number of RLC SDU's for fourth cell secondary flow
	}
}

--**************************************************************
--
-- CRLC-BindTestDataInMultipleMACehs-PDU-NodeB-CNF
-- To confirm the request of binding subsequent data sending RLC-TR/UM/AM-TestDataReq on the specified RB mapped on HS-DSCH.
--
--**************************************************************
CRLC-BindTestDataInMultipleMACehs-PDU-NodeB-CNF ::= SEQUENCE{
	cellId			INTEGER(-1..63),
	routingInfo		RoutingInfo,			-- RB ID
	result			ENUMERATED{failure(0), success(1)}
}

--**************************************************************
--
-- CRLC-BindTestDataInMultipleMACehs-PDU-NodeB-REQ
-- To request of binding subsequent data sending RLC-TR/UM/AM-TestDataReq on the specified RB mapped on up to 4 HS-DSCH configured on one or two NodeB in simultaneous MAC-ehs PDUs.
-- On the request, the transmission of the test data is temporarily suppressed on the radio bearer till all SDUs for all flows are received by RLC layer on the Radio Bearer. After receiving all SDU's the RLC layer submits to MAC such that all of them are sent in MAC-ehs PDUs at the same timing.
--
--**************************************************************
CRLC-BindTestDataInMultipleMACehs-PDU-NodeB-REQ ::= SEQUENCE{
    cellId			INTEGER(-1..63),
 	routingInfo		RoutingInfo,		-- RB ID desired to be given
	bindingNodeB	SEQUENCE (SIZE (1..2)) OF NodeB-FlowList-Type
}

--**************************************************************
--
-- NodeB-FlowList-Type
--
--**************************************************************
NodeB-FlowList-Type ::= SEQUENCE {
	nodeB-Id						INTEGER(0..63),
	servingFlowNumOfSDUs			INTEGER		OPTIONAL,
		-- Number of RLC SDU's for the serving HS-DSCH cell
	assistingServingFlowNumOfSDUs	INTEGER 	OPTIONAL,
		-- Number of RLC SDU's for the assisting serving HS-DSCH cell
	secondaryFlowNumOfSDUs			INTEGER		OPTIONAL,
		-- Number of RLC SDU's for the secondary serving HS-DSCH cell
	assistingSecondaryFlowNumOfSDUs	INTEGER		OPTIONAL
		-- Number of RLC SDU's for the assisting secondary serving HS-DSCH cell
}

--**************************************************************
-- PDCP ASPs
--**************************************************************
--**************************************************************
-- 
-- CPDCP-Config-CNF
-- For PDCP emulator to report that a previous attempt to setup, reconfigure or release a logical channel is successful.
--
--**************************************************************
CPDCP-Config-CNF ::= SEQUENCE	{
	cellId	INTEGER(-1..63),
	routingInfo	RoutingInfo
}

--**************************************************************
-- 
-- CPDCP-Config-REQ
-- To request to configure PDCP entity. Setup is used for creation of the PDCP instances or the PDCP resources. 
-- Release is used for free the all PDCP resources. 
-- The reconfiguration is to change the PDCP parameters. 
-- PDCP entity does not belong to a particular cell, the cellId shall assign the value -1. 
-- The routingInfo is RB identity which is used to connect this PDCP entity to the RLC entity with the same RB identity and it is also used for PDCP-DATA-REQ ASP to transmit data through this PDCP entity.
--
--**************************************************************
CPDCP-Config-REQ ::= SEQUENCE	{
	cellId						INTEGER(-1..63),
	routingInfo					RoutingInfo,
	ratType						RatType,
	configMessage				CHOICE {
		setup						SS-PDCP-Info,
		reconfigure					SS-PDCP-InfoReconfig,
		release						NULL
	}
}

--**************************************************************
-- 
-- SS-PDCP-Info
-- When configuring downlink direction of the SS, the UL-RFC3095-r4 shall be used; when configuring uplink direction of the SS the DL-RFC3095-r4 shall be used. 
--
--**************************************************************
SS-PDCP-Info ::= SEQUENCE	{
	pDCP-ROHC-TargetMode	PDCP-ROHC-TargetMode OPTIONAL,
	pDCP-Info				PDCP-Info-r4,
	cSVoHS-Info				CS-HSPA-Information OPTIONAL	-- Rel-7 or later
}

--**************************************************************
-- 
-- SS-PDCP-InfoReconfig
-- When configuring downlink direction of the SS, the UL-RFC3095-r4 shall be used; when configuring uplink direction of the SS the DL-RFC3095-r4 shall be used.
--
--**************************************************************
SS-PDCP-InfoReconfig ::= SEQUENCE	{
	pDCP-ROHC-TargetMode	PDCP-ROHC-TargetMode OPTIONAL, --@sic R5w140013 sic@
	pDCP-Info				PDCP-InfoReconfig-r4,
	cSVoHS-Info				CS-HSPA-Information OPTIONAL	-- Rel-7 or later
}

END
