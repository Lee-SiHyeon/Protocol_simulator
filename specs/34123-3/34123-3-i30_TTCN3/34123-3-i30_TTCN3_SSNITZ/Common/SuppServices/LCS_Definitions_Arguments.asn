LCS-Definitions-Arguments DEFINITIONS  ::=

BEGIN

IMPORTS 
AddressString,
maxAddressLength,
ExtensionContainer,
PrivateExtensionList,
PrivateExtension,
maxNumOfPrivateExtensions,
PCS-Extensions,
USSD-DataCodingScheme,
USSD-String,
maxUSSD-StringLength,
ISDN-AddressString
FROM Common-Definitions-Arguments;
								
--*****************************************************
--Derived from SS-DataTypes in 3GPP TS 24.080
--*****************************************************

LocationNotificationArg	::= SEQUENCE {
	notificationType			[0] IMPLICIT NotificationToMSUser,
	locationType				[1] IMPLICIT LocationType,
	lcsClientExternalID			[2] IMPLICIT LCSClientExternalID	OPTIONAL,
	lcsClientName				[3] IMPLICIT LCSClientName		OPTIONAL,
	...,
	lcsRequestorID				[4] IMPLICIT LCSRequestorID		OPTIONAL,
	lcsCodeword					[5] IMPLICIT LCSCodeword			OPTIONAL,
	lcsServiceTypeID			[6] IMPLICIT LCSServiceTypeID	OPTIONAL,
    deferredLocationExt         [7] IMPLICIT DeferredLocationExt  OPTIONAL, -- @sic R5s170598 Baseline Moving sic@
    rangingSlExt                [8] IMPLICIT RangingSlExt         OPTIONAL  -- @sic R5s240534 Baseline Moving sic@
	}
-- The notificationType may only be set to notifyLocationAllowed, 
-- notifyAndVerify-LocationAllowedIfNoResponse, 
-- or notifyAndVerify-LocationNotAllowedIfNoResponse.
-- The locationEstimateType field of the locationType may only be set to 
-- currentLocation, currentOrLastKnownLocation, 
-- notificationVerificationOnly, or activateDeferredLocation.
-- The deferredLocationEventType field of the locationType may only be set to 
-- enteringIntoArea, and/or leavingFromArea, and/or beingInsideArea, 
-- and/or periodicLDR.
-- For LCS location notification of MT-LR for current location, the 
-- locationEstimateType field of the locationType shall be set to currentLocation.
-- For LCS location notification of MT-LR for current or last known location, the 
-- locationEstimateType field of the locationType shall be set to currentOrLastKnownLocation.
-- For the LCS location notification for the LDR of MS available event, 
-- the locationEstimateType field of the locationType shall be set to currentLocation.
-- For LCS location notification for the LDR of change of area event, 
-- the locationEstimateType field of the locationType shall be set to
-- activateDeferredLocation, and the deferredLocationEventType shall be 
-- set to enteringIntoArea, and/or leavingFromArea, and/or beingInsideArea.
-- For the post positioning LCS location notification, the locationEstimateType 
-- field of the locationType shall be set to notificationVerificationOnly.
-- For LCS location notification for the LDR of periodic location event, 
-- the locationEstimateType field of the locationType shall be set to
-- activateDeferredLocation, and the 
-- deferredLocationEventType shall be set to periodicLDR.
-- For LCS location notification for the LDR of the motion event, 
-- the locationEstimateType field of the locationType shall be set to
-- activateDeferredLocation, the deferredLocationEventType shall be omitted
-- and the deferredLocationExt shall be set to motionEvent.

-- exception handling:
-- At reception of an unrecognised notificationType value the receiver shall reject the 
-- operation with a return error cause of unexpected data value.
-- At reception of an unrecognised locationType value the receiver shall reject the
-- operation with a return error cause of unexpected data value. 
-- At reception of an unallowed notificationType value the receiver shall either ignore the
-- received operation or reject the operation with a return error cause of unexpected 
-- data value.
-- At reception of an unallowed locationType value the receiver shall either ignore the
-- received operation or reject the operation with a return error cause of unexpected 
-- data value.

DeferredLocationExt ::= BIT STRING {
	motionEvent	(0) } (SIZE (1..16)) 
-- A bit set to one indicates that the corresponding deferred location type is present.
-- A bit set to zero indicates that the corresponding deferred location type is absent.

RangingSlExt ::= BIT STRING {
	rangingIndication	(0) } (SIZE (1..16))
-- A bit set to one indicates that the notification is for ranging and sidelink positioning.

LocationNotificationRes  ::= SEQUENCE {
	verificationResponse	[0] IMPLICIT VerificationResponse OPTIONAL,
    locationPrivacyIndication	[1] LCS-LocationPrivacyIndication	OPTIONAL, -- @sic R5s20xxxx sic@
	validTimePeriod		[2] LCS-ValidTimePeriod	OPTIONAL,
	...}
-- Parameters locationPrivacyIndication or validTimePeriod may be included by a UE for 5GS 
-- access. Parameter validTimePeriod only may be included if parameter locatonPrivacyIndication 
-- is included

VerificationResponse::= ENUMERATED {
	permissionDenied (0),
	permissionGranted (1),
	...
	}
	 -- exception handling:
	 -- an unrecognized value shall be treated the same as value 0 (permissionDenied)

LCS-LocationPrivacyIndication ::= ENUMERATED {
	locationDisallowed (0),
	locationAllowed (1),
	...,
	rangingDisallowed (2),   -- @sic R5s240534 Baseline Moving sic@
	rangingAllowed (3) 
	}

LCS-ValidTimePeriod ::= SEQUENCE {
	startTime	[0] DateTime	OPTIONAL,
	endTime	[1] DateTime	OPTIONAL,
	... }

DateTime ::= OCTET STRING (SIZE (30))   --  @sic R5s221182 Baseline Moving sic@
-- The timestamp at which certain event occurs. Octets are coded according to RFC 3339 [18]

LCS-MOLRArg	::= SEQUENCE {
	molr-Type			[0] IMPLICIT	MOLR-Type,
	locationMethod		[1] IMPLICIT	LocationMethod			OPTIONAL,
	lcs-QoS				[2] IMPLICIT	LCS-QoS				OPTIONAL,
	lcsClientExternalID	[3] IMPLICIT 	LCSClientExternalID		OPTIONAL,
	mlc-Number			[4] IMPLICIT	ISDN-AddressString		OPTIONAL,
	gpsAssistanceData	[5] IMPLICIT	GPSAssistanceData		OPTIONAL,
	...,
	supportedGADShapes	[6] IMPLICIT	SupportedGADShapes		OPTIONAL,
	lcsServiceTypeID	[7] IMPLICIT LCSServiceTypeID		OPTIONAL,
	ageOfLocationInfo	[8] IMPLICIT AgeOfLocationInformation	OPTIONAL,
	locationType		[9] IMPLICIT LocationType			OPTIONAL,
	pseudonymIndicator	[10] IMPLICIT NULL					OPTIONAL,
	h-gmlc-address 		[11] IMPLICIT GSN-Address			OPTIONAL,
	locationEstimate	[12] IMPLICIT Ext-GeographicalInformation		OPTIONAL,
	velocityEstimate	[13] IMPLICIT VelocityEstimate-AGPS		OPTIONAL,
	referenceNumber 	[14] IMPLICIT LCS-ReferenceNumber 	OPTIONAL,
	periodicLDRInfo		[15] IMPLICIT PeriodicLDRInfo		OPTIONAL,
	locationUpdateRequest	[16]	IMPLICIT NULL				OPTIONAL,
	sequenceNumber 		[17] IMPLICIT SequenceNumber		OPTIONAL,
	terminationCause 	[18] IMPLICIT TerminationCause 		OPTIONAL,
	mo-lrShortCircuit	[19] IMPLICIT NULL				OPTIONAL,
	ganssAssistanceData	[20] IMPLICIT GANSSAssistanceData	OPTIONAL,
	multiplePositioningProtocolPDUs	[21] IMPLICIT MultiplePositioningProtocolPDUs	OPTIONAL, --@sic R5s151010 sic@
	locationInfo		[22] LocationInfo			OPTIONAL,  --  @sic R5s170598 Baseline Moving sic@
    scheduledLocTime    [23] DateTime               OPTIONAL  --  @sic R5s221182 Baseline Moving sic@
    }
	 -- The parameter locationMethod shall be included if and only if the 
	 -- molr-Type is set to value deCipheringKeys or assistanceData.
	 -- The parameter gpsAssistanceData shall be included if and only if the
	 -- molr-Type is set to value assistanceData and 
	 -- locationMethod is set to value assistedGPS or assistedGPSandGANSS.
	-- The parameter ganssAssistanceData shall be included if and only if the molr-Type is set to value 
	-- assistanceData and locationMethod is set to value assistedGANSS or assistedGPSandGANSS.
	-- supportedGADShapes shall not be included for deferred MO-LR initiation or deferred MO-LR or MT-LR
	-- responses.
	-- multiplePositioningProtocolPDUs may only be included for E-UTRAN access.
	-- locationMethod shall not be included for E-UTRAN access.
	-- gpsAssistanceData shall not be included for E-UTRAN access.
	-- velocityEstimate shall not be included for E-UTRAN access.
	-- periodicLDRInfo shall not be included for E-UTRAN access.
	-- locationUpdateRequest shall not be included for E-UTRAN access.
	-- sequenceNumber shall not be included for E-UTRAN access.
	-- mo-lrShortCircuit shall not be included for E-UTRAN access.
	-- ganssAssistanceData shall not be included for E-UTRAN access.
    -- locationInfo shall be included if available for E-UTRAN access for a periodic and triggered
    -- event report.
    -- Only mlc-number could be used to represent the address of H-GMLC of the UE, h-gmlc-address shall not be used for this purpose.
    -- if mappedQoSEps was received in LCS-PeriodicTriggeredInvokeArg to initiate deferred location event reporting from 5GS, lcs-QoS shall be set to the value of the received mappedQoSEps when a correspoding event is to be reported in EPS.

MOLR-Type ::= ENUMERATED {
	locationEstimate (0), 
	assistanceData (1), 
	deCipheringKeys (2),
	...,
	deferredMo-lrTTTPInitiation	(3),
	deferredMo-lrSelfLocationInitiation (4),
	deferredMt-lrOrmo-lrTTTPLocationEstimate (5),
	deferredMt-lrOrmo-lrCancellation (6),
    periodicEvent (7), --  @sic R5s170598 Baseline Moving sic@
	enteringAreaEvent (8),
	leavingAreaEvent (9),
	beingInsideAreaEvent (10),
	motionEvent (11),
	maximumIntervalExpirationEvent (12)
	}
	 -- exception handling:
	 -- an unrecognized value shall be rejected by the receiver with a return error cause of
	 -- unexpected data value.
     -- For E-UTRAN access, only locationEstimate, assistanceData, periodicEvent,
     -- deferredMt-lrOrmo-lrCancellation, enteringAreaEvent, leavingAreaEvent, beingInsideAreaEvent,
     -- motionEvent or maximumIntervalExpirationEvent shall be included

LocationInfo ::= BIT STRING {
	locationEstimate	(0) } (SIZE (1..32)) 
-- A bit set to one indicates that the corresponding requirement is present.
-- A bit set to zero indicates that the corresponding requirement is absent.
-- The locationEstimate is a requirement to provide the UE location for an event report to
-- the external client, but the location may be provided by either the UE or network.
     
LocationMethod ::= ENUMERATED {
	msBasedEOTD	(0), 
	msAssistedEOTD (1), 
	assistedGPS	(2),
	...,
	msBasedOTDOA	(3) ,
	assistedGANSS	(4),
	assistedGPSandGANSS	(5) 
	}
	 -- exception handling:
	 -- When this parameter is received with value msBasedEOTD or msAssistedEOTD and the MS 
	 -- is camped on an UMTS Service Area then the receiver shall reject it 
	 -- with a return error cause of unexpected data value.
	 -- When this parameter is received with value msBasedOTDOA and the MS 
	 -- is camped on a GSM Cell then the receiver shall reject it with 
	 -- a return error cause of unexpected data value.
	 -- an unrecognized value shall be rejected by the receiver with 
	 -- a return error cause of unexpected data value.

GPSAssistanceData ::= OCTET STRING (SIZE (1..38))
	 -- Octets 1 to 38 are coded in the same way as the octets 3 to 7+2n 
	 -- of Requested GPS Data IE in 3GPP TS 49.031.

GANSSAssistanceData::= OCTET STRING (SIZE (1..40))
-- Octets 1 to 40 are coded in the same way as the octets 3 to 9+2n of Requested GANSS Data IE
-- in 3GPP TS 49.031 [14] .

TerminationCause ::= ENUMERATED {
	subscriberTermination  (0),
	uETermination  (1),
...,
	normalTermination  (2),  -- @sic R5s20xxxx sic@
	networkTermination  (3)} 
-- normalTermination shall be included for a normal end to periodic or triggered event
-- reporting

MultiplePositioningProtocolPDUs ::= SEQUENCE (SIZE (1..maxNumLPPMsg)) OF PositioningProtocolPDU

PositioningProtocolPDU ::= OCTET STRING
-- PositioningProtocolPDU contains a LPP message defined in 3GPP TS 36.355 [17].

maxNumLPPMsg INTEGER ::= 3


LCS-MOLRRes ::= SEQUENCE {
	locationEstimate		[0] IMPLICIT Ext-GeographicalInformation	OPTIONAL,
	decipheringKeys			[1] IMPLICIT DecipheringKeys			OPTIONAL,
	...,
	add-LocationEstimate	[2] IMPLICIT Add-GeographicalInformation 	OPTIONAL,
	velocityEstimate		[3] IMPLICIT VelocityEstimate-AGPS		OPTIONAL,
	referenceNumber 		[4] IMPLICIT LCS-ReferenceNumber 	OPTIONAL,
	h-gmlc-address			[5]	IMPLICIT GSN-Address				OPTIONAL,
	mo-lrShortCircuit		[6]	IMPLICIT NULL					OPTIONAL,
	reportingPLMNList		[7]	IMPLICIT ReportingPLMNList		OPTIONAL,
    timestampOfLocationEstimate	[8]	DateTime	                OPTIONAL   --  @sic R5s221182 Baseline Moving sic@
	}
	
	 -- Parameters locationEstimate or add-LocationEstimate (one but not both) 
	 -- shall be included if and only if the 
	 -- molr-Type in LocationRequestArg was set to value locationEstimate.
	 -- Parameter add-LocationEstimate shall not be included 
	 -- if the supportedGADShapes parameter was not received in the LCS-MOLRArg.
	 -- The locationEstimate and the add-locationEstimate parameters shall not be
	 -- sent if the supportedGADShapes parameter has been received in LCS-MOLRArg
	 -- and the shape encoded in locationEstimate or add-LocationEstimate 
	 -- is not marked as supported in supportedGADShapes.
	 -- In such a case LCS-MOLRArg shall be rejected with error
	 -- FacilityNotSupported with additional indication
 	 -- shapeOfLocationEstimateNotSupported.
	 -- Parameter decipheringKeys shall be included if and only if the molr-Type
	 -- in LocationRequestArg was set to value deCipheringKeys.	
	 -- Parameter velocityEstimate may only be included if the lcs-QoS in LCS-MOLRarg includes
	-- velocityRequest


DecipheringKeys ::= OCTET STRING (SIZE (15))
	 -- Octets in DecipheringKeys are coded in the same way as the octets 3 to 17 
	 -- of Deciphering Key IE in 3GPP TS 49.031. I.e. these octets contain 
	 -- Current Deciphering Key, Next Deciphering Key and Ciphering Key Flag.


--********************************************************
-- Derived from MAP-Errors 3GPP 29.002
--********************************************************

SystemFailureParam ::= CHOICE {
	networkResource						NetworkResource,
	-- networkResource must not be used in version 3
	extensibleSystemFailureParam		ExtensibleSystemFailureParam
	-- extensibleSystemFailureParam must not be used in version <3
	}

NetworkResource ::= ENUMERATED {
	plmn (0),
	hlr (1),
	vlr (2),
	pvlr (3),
	controllingMSC (4),
	vmsc (5),
	eir (6),
	rss (7)
	}

ExtensibleSystemFailureParam ::= SEQUENCE {
	networkResource				NetworkResource		OPTIONAL,
	extensionContainer			ExtensionContainer	OPTIONAL,
	...,
	additionalNetworkResource	[0] AdditionalNetworkResource	OPTIONAL,
	failureCauseParam			[1] FailureCauseParam	OPTIONAL
   }
   
AdditionalNetworkResource ::= ENUMERATED {
	sgsn (0),
	ggsn (1),
	gmlc (2),
	gsmSCF (3),
	nplr (4),
	auc (5),
	...,
	ue (6),
	mme (7)
	}
	-- if unknown value is received in AdditionalNetworkResource
	-- it shall be ignored.

FailureCauseParam ::= ENUMERATED {
	limitReachedOnNumberOfConcurrentLocationRequests (0),
	... }
	-- if unknown value is received in FailureCauseParam it shall be ignored

UnexpectedDataParam ::= SEQUENCE {
			extensionContainer		ExtensionContainer	OPTIONAL,
			...,
			unexpectedSubscriber 	[0]	 NULL			OPTIONAL
	}
-- the unexpectedSubscriber indication in the unexpectedDataValue error shall not be used
-- for operations that allow the unidentifiedSubscriber error.

DataMissingParam ::= SEQUENCE {
			extensionContainer		ExtensionContainer	OPTIONAL,
			...
			}

FacilityNotSupParam ::= SEQUENCE {
	extensionContainer								ExtensionContainer	OPTIONAL,
	...,
	shapeOfLocationEstimateNotSupported 			[0] IMPLICIT NULL	OPTIONAL,
	neededLcsCapabilityNotSupportedInServingNode 	[1] IMPLICIT NULL	OPTIONAL
	}


SS-SubscriptionViolationParam ::= SEQUENCE {
			extensionContainer		ExtensionContainer	OPTIONAL,
			... 
			}


PositionMethodFailure-Param ::= SEQUENCE {
	positionMethodFailure-Diagnostic	[0] IMPLICIT PositionMethodFailure-Diagnostic	OPTIONAL,
	extensionContainer					[1] IMPLICIT ExtensionContainer			OPTIONAL,
	...
	}

PositionMethodFailure-Diagnostic ::= ENUMERATED {
	congestion (0),
	insufficientResources (1),
	insufficientMeasurementData (2),
	inconsistentMeasurementData (3),
	locationProcedureNotCompleted (4),
	locationProcedureNotSupportedByTargetMS (5),
	qoSNotAttainable (6),
	positionMethodNotAvailableInNetwork (7),
	positionMethodNotAvailableInLocationArea (8),
	...
	}
	-- exception handling:
	-- any unrecognized value shall be ignored

--*******************************************************
-- From 3GPP TS 29.002
--*******************************************************

NotificationToMSUser ::= ENUMERATED {
	notifyLocationAllowed (0),
	notifyAndVerify-LocationAllowedIfNoResponse (1),
	notifyAndVerify-LocationNotAllowedIfNoResponse (2),
	...,
	locationNotAllowed (3) }
	 -- exception handling:
	 -- At reception of any other value than the ones listed the receiver shall ignore
	 -- NotificationToMSUser.

LocationType ::= SEQUENCE {
	locationEstimateType		[0] IMPLICIT LocationEstimateType,
	...,
	deferredLocationEventType	[1] IMPLICIT DeferredLocationEventType	OPTIONAL }

LocationEstimateType ::= ENUMERATED {
	currentLocation (0),
	currentOrLastKnownLocation (1),
	initialLocation (2),
	...,
	activateDeferredLocation (3),
	cancelDeferredLocation (4),
	notificationVerificationOnly	(5)
 }
	 -- exception handling:
	 -- a ProvideSubscriberLocation-Arg containing an unrecognized LocationEstimateType
	 -- shall be rejected by the receiver with a return error cause of unexpected data value

DeferredLocationEventType ::= BIT STRING {
	msAvailable (0),
	enteringIntoArea	(1),
	leavingFromArea	(2),
	beingInsideArea	(3) ,
	periodicLDR	(4)
 	} (SIZE (1..16))
	-- beingInsideArea is always treated as oneTimeEvent regardless of the possible value
	-- of occurrenceInfo inside areaEventInfo.
	-- exception handling:
	-- a ProvideSubscriberLocation-Arg containing other values than listed above in 
	-- DeferredLocationEventType shall be rejected by the receiver with a return error cause of 
	-- unexpected data value.


LCSClientExternalID ::= SEQUENCE {
	externalAddress		[0] IMPLICIT ISDN-AddressString	OPTIONAL,
	extensionContainer	[1] IMPLICIT ExtensionContainer	OPTIONAL,
	...
	}

LCSClientName ::= SEQUENCE {
	dataCodingScheme	[0] IMPLICIT USSD-DataCodingScheme,
	nameString			[2] IMPLICIT NameString,
	...,
	lcs-FormatIndicator	[3] IMPLICIT LCS-FormatIndicator	OPTIONAL 
	}

	 -- The USSD-DataCodingScheme shall indicate use of the default alphabet through the following encoding
	 --	bit	7 6 5 4 3 2 1 0
	 --			0 0 0 0 1 1 1 1

NameString ::= USSD-String (SIZE (1..maxNameStringLength))

maxNameStringLength  INTEGER ::= 63

LCSRequestorID ::= SEQUENCE {
	dataCodingScheme		[0] IMPLICIT USSD-DataCodingScheme,
	requestorIDString		[1] IMPLICIT RequestorIDString,
	...,
	lcs-FormatIndicator		[2] IMPLICIT LCS-FormatIndicator	OPTIONAL
	}

LCS-FormatIndicator ::= ENUMERATED {
	logicalName		(0),
	e-mailAddress	(1),
	msisdn			(2),
	url				(3),
	sipUrl			(4),
	... }

RequestorIDString ::= USSD-String (SIZE (1..maxRequestorIDStringLength))

maxRequestorIDStringLength  INTEGER ::= 63

LCSCodeword ::= SEQUENCE {
	dataCodingScheme		[0] IMPLICIT USSD-DataCodingScheme,
	lcsCodewordString		[1] IMPLICIT LCSCodewordString,
	...
	}
	
LCSCodewordString ::= USSD-String (SIZE (1..maxLCSCodewordStringLength))

maxLCSCodewordStringLength  INTEGER ::= 20

LCSServiceTypeID ::= INTEGER (0..127)
	-- the integer values 0-63 are reserved for Standard LCS service types
	-- the integer values 64-127 are reserved for Non Standard LCS service types

LCS-QoS ::= SEQUENCE {
	horizontal-accuracy			[0] IMPLICIT Horizontal-Accuracy	OPTIONAL,
	verticalCoordinateRequest	[1] IMPLICIT NULL		OPTIONAL,
	vertical-accuracy			[2] IMPLICIT Vertical-Accuracy	OPTIONAL,
	responseTime				[3] IMPLICIT ResponseTime	OPTIONAL,
	extensionContainer			[4] IMPLICIT ExtensionContainer	OPTIONAL,
	...,
	velocityRequest				[5] IMPLICIT NULL		OPTIONAL,
    lcs-qos-class	            [6] LCS-QoS-Class	OPTIONAL    -- @sic R5s240534 Baseline Moving sic@
}
-- lcs-qos-class may only be included in MO-LR request sent by the UE to the network.



Horizontal-Accuracy ::= OCTET STRING (SIZE (1))
	-- bit 8 = 0
	-- bits 7-1 = 7 bit Uncertainty Code defined in 3GPP TS 23.032. The horizontal location 
	-- error should be less than the error indicated by the uncertainty code with 67%
	-- confidence.

Vertical-Accuracy ::= OCTET STRING (SIZE (1))
	-- bit 8 = 0
	-- bits 7-1 = 7 bit Vertical Uncertainty Code defined in 3GPP TS 23.032. 
	-- The vertical location error should be less than the error indicated 
	-- by the uncertainty code with 67% confidence.

ResponseTime ::= SEQUENCE {
	responseTimeCategory		ResponseTimeCategory,
	...
	}
	 -- note: an expandable SEQUENCE simplifies later addition of a numeric response time.

ResponseTimeCategory ::= ENUMERATED {
	lowdelay (0),
	delaytolerant (1),
	...}
	 -- exception handling:
	 -- an unrecognized value shall be treated the same as value 1 (delaytolerant)

SupportedGADShapes ::= BIT STRING {
	ellipsoidPoint (0),
	ellipsoidPointWithUncertaintyCircle (1),
	ellipsoidPointWithUncertaintyEllipse (2),
	polygon (3),
	ellipsoidPointWithAltitude (4),
	ellipsoidPointWithAltitudeAndUncertaintyElipsoid (5),
	ellipsoidArc (6) } (SIZE (7..16))
	 -- A node shall mark in the BIT STRING all Shapes defined in 3GPP TS 23.032 it supports.
	 -- exception handling: bits 7 to 15 shall be ignored if received.

Ext-GeographicalInformation ::= OCTET STRING (SIZE (1..maxExt-GeographicalInformation))
	-- Refers to geographical Information defined in 3GPP TS 23.032.
	-- This is composed of 1 or more octets with an internal structure according to
	-- 3GPP TS 23.032
	-- Octet 1: Type of shape, only the following shapes in 3GPP TS 23.032 are allowed:
	--		(a) Ellipsoid point with uncertainty circle
	--		(b) Ellipsoid point with uncertainty ellipse
	--		(c) Ellipsoid point with altitude and uncertainty ellipsoid
	--		(d) Ellipsoid Arc
	--		(e) Ellipsoid Point
	-- Any other value in octet 1 shall be treated as invalid
	-- Octets 2 to 8 for case (a)  Ellipsoid point with uncertainty circle
	--		Degrees of Latitude				3 octets
	--		Degrees of Longitude				3 octets
	--		Uncertainty code				1 octet
	-- Octets 2 to 11 for case (b)  Ellipsoid point with uncertainty ellipse:
	--		Degrees of Latitude				3 octets
	--		Degrees of Longitude				3 octets
	--		Uncertainty semi-major axis				1 octet
	--		Uncertainty semi-minor axis				1 octet
	--		Angle of major axis				1 octet
	--		Confidence				1 octet
	-- Octets 2 to 14 for case (c)  Ellipsoid point with altitude and uncertainty ellipsoid
	--		Degrees of Latitude				3 octets
	--		Degrees of Longitude				3 octets
	--		Altitude				2 octets
	--		Uncertainty semi-major axis				1 octet
	--		Uncertainty semi-minor axis				1 octet
	--		Angle of major axis				1 octet
	--		Uncertainty altitude				1 octet
	--		Confidence				1 octet
	-- Octets 2 to 13 for case (d)  Ellipsoid Arc
	--		Degrees of Latitude				3 octets
	--		Degrees of Longitude				3 octets
	--		Inner radius				2 octets
	--		Uncertainty radius				1 octet
	--		Offset angle				1 octet
	--		Included angle				1 octet
	--		Confidence				1 octet
	-- Octets 2 to 7 for case (e)  Ellipsoid Point
	--		Degrees of Latitude				3 octets
	--		Degrees of Longitude				3 octets

	--
	-- An Ext-GeographicalInformation parameter comprising more than one octet and
	-- containing any other shape or an incorrect number of octets or coding according
	-- to 3GPP TS 23.032 shall be treated as invalid data by a receiver.
	--
	-- An Ext-GeographicalInformation parameter comprising one octet shall be discarded
	-- by the receiver if an Add-GeographicalInformation parameter is received 
	-- in the same message.
	--
	-- An Ext-GeographicalInformation parameter comprising one octet shall be treated as
	-- invalid data by the receiver if an Add-GeographicalInformation parameter is not
	-- received in the same message.

maxExt-GeographicalInformation  INTEGER ::= 20
	-- the maximum length allows for further shapes in 3GPP TS 23.032 to be included in later 
	-- versions of 3GPP TS 29.002

Add-GeographicalInformation ::= OCTET STRING (SIZE (1..maxAdd-GeographicalInformation))
	-- Refers to geographical Information defined in 3GPP TS 23.032.
	-- This is composed of 1 or more octets with an internal structure according to 
	-- 3GPP TS 23.032
	-- Octet 1: Type of shape, all the shapes defined in 3GPP TS 23.032 are allowed:
	-- Octets 2 to n (where n is the total number of octets necessary to encode the shape
	-- according to 3GPP TS 23.032) are used to encode the shape itself in accordance with the
	-- encoding defined in 3GPP TS 23.032
	--
	-- An Add-GeographicalInformation parameter, whether valid or invalid, received 
	-- together with a valid Ext-GeographicalInformation parameter in the same message 
	-- shall be discarded.
	--
	-- An Add-GeographicalInformation parameter containing any shape not defined in 
	-- 3GPP TS 23.032 or an incorrect number of octets or coding according to 
	-- 3GPP TS 23.032 shall be treated as invalid data by a receiver if not received 
	-- together with a valid Ext-GeographicalInformation parameter in the same message.

maxAdd-GeographicalInformation  INTEGER ::= 91
	-- the maximum length allows support for all the shapes currently defined in 3GPP TS 23.032

AgeOfLocationInformation ::= INTEGER (0..32767)
	-- the value represents the elapsed time in minutes since the last 
	-- network contact of the mobile station (i.e. the actuality of the 
	-- location information).
	-- value "0" indicates that the MS is currently in contact with the network 
	-- "32767" indicates that the location information is at least 32767 minutes old 

GSN-Address ::= OCTET STRING (SIZE (5..17))
	-- Octets are coded according to TS 3GPP TS 23.003

LCS-ReferenceNumber ::= OCTET STRING (SIZE(1))

PeriodicLDRInfo  ::= SEQUENCE {
	reportingAmount		ReportingAmount-AGPS,
	reportingInterval	ReportingInterval-AGPS,
	...,
    reportingOptionMilliseconds	[0]	ReportingOptionMilliseconds	OPTIONAL     -- @sic R5s240534 Baseline Moving sic@
	}
	-- reportingInterval x reportingAmount shall not exceed 8639999 (99 days, 23 hours,
	-- 59 minutes and 59 seconds) for compatibility with OMA MLP and RLP 
    -- When reportingOptionMilliseconds is provided and supported, reportingInterval & 
    -- reportingAmount shall be ignored.

ReportingAmount-AGPS ::= INTEGER (1..maxReportingAmount)

maxReportingAmount INTEGER ::= 8639999

ReportingInterval-AGPS ::= INTEGER (1..maxReportingInterval)
	-- ReportingInterval is in seconds

maxReportingInterval INTEGER ::= 8639999 

ReportingOptionMilliseconds ::= SEQUENCE {
	reportingAmountMilliseconds	ReportingAmountMilliseconds,
	reportingIntervalMilliseconds	ReportingIntervalMilliseconds,
	...}
-- reportingAmountMilliseconds x reportingIntervalMilliseconds shall not exceed 8639999000 
-- (99 days, 23 hours, 59 minutes and 59 seconds) for compatibility with OMA MLP and RLP

ReportingAmountMilliseconds ::= INTEGER (1..maxReportingAmountMilliseconds)

maxReportingAmountMilliseconds INTEGER ::= 8639999000

ReportingIntervalMilliseconds ::= INTEGER (1..maxReportingIntervalMilliseconds)

maxReportingIntervalMilliseconds INTEGER ::= 999

VelocityEstimate-AGPS ::= OCTET STRING (SIZE (4..7))
	-- Refers to Velocity description defined in 3GPP TS 23.032.
	-- This is composed of 4 or more octets with an internal structure according to
	-- 3GPP TS 23.032
	-- Octet 1: Type of velocity, only the following types in 3GPP TS 23.032 are allowed:
	--		(a) Horizontal Velocity
	--		(b) Horizontal with Vertical Velocity
	--		(c) Horizontal Velocity with Uncertainty
	--		(d) Horizontal with Vertical Velocity and Uncertainty
	-- For types Horizontal with Vertical Velocity and Horizontal with Vertical Velocity
	-- and Uncertainty, the direction of the Vertical Speed is also included in Octet 1
	-- Any other value in octet 1 shall be treated as invalid
	-- Octets 2 to 4 for case (a) Horizontal velocity:
	--		Bearing				1 octet
	--		Horizontal Speed				2 octets
	-- Octets 2 to 5 for case (b)  Horizontal with Vertical Velocity:
	--		Bearing				1 octet
	--		Horizontal Speed				2 octets
	--		Vertical Speed				1 octet
	-- Octets 2 to 5 for case (c)  Horizontal velocity with Uncertainty:
	--		Bearing				1 octet
	--		Horizontal Speed				2 octets
	--		Uncertainty Speed				1 octet
	-- Octets 2 to 7 for case (d)  Horizontal with Vertical Velocity and Uncertainty:
	--		Bearing				1 octet
	--		Horizontal Speed				2 octets
	--		Vertical Speed				1 octet
	--		Horizontal Uncertainty Speed			1 octet
	--		Vertical Uncertainty Speed				1 octet

SequenceNumber ::= INTEGER (1..maxReportingAmount)

ReportingPLMNList::= SEQUENCE {
	plmn-ListPrioritized			[0] NULL					OPTIONAL,
	plmn-List 						[1] PLMNList 
	}

PLMNList::= SEQUENCE SIZE (1..maxNumOfReportingPLMN) OF
				ReportingPLMN

maxNumOfReportingPLMN INTEGER ::= 20

ReportingPLMN::= SEQUENCE {
	plmn-Id 						[0] PLMN-Id,
	ran-Technology 					[1] RAN-Technology			OPTIONAL,
	ran-PeriodicLocationSupport		[2] NULL					OPTIONAL,
	...
	}
	
RAN-Technology ::= ENUMERATED {
	gsm			(0),
	umts		(1),
	... }

PLMN-Id ::= OCTET STRING (SIZE (3))
	-- The internal structure is defined as follows:
	-- octet 1 bits 4321	Mobile Country Code 1st digit
	--         bits 8765	Mobile Country Code 2nd digit
	-- octet 2 bits 4321	Mobile Country Code 3rd digit
	--         bits 8765	Mobile Network Code 3rd digit
	--			or filler (1111) for 2 digit MNCs
	-- octet 3 bits 4321	Mobile Network Code 1st digit
	--         bits 8765	Mobile Network Code 2nd digit

LCS-QoS-Class ::= ENUMERATED {
	bestEffort  (0),
	assured  (1),
	... }
--	exception handling:
--	an unrecognized value shall be treated the same as value 0 (bestEffort)


END
